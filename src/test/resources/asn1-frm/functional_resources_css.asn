CSTS-FUNCTIONAL-RESOURCE-TYPES
{ iso(1) identified-organization(3) standards-producing-organization(112)
	ccsds(4) css(4) crossSuppportResources(2)
}

DEFINITIONS
IMPLICIT TAGS
::= BEGIN

EXPORTS
	 	 antennaFrOid
,	 	 AntResourceStat
,	 	 antResourceStatParamOid
,	 	 AntId
,	 	 antIdParamOid
,	 	 AntActualAzimuth
,	 	 antActualAzimuthParamOid
,	 	 AntActualElevation
,	 	 antActualElevationParamOid
,	 	 AntCommandedAzimuth
,	 	 antCommandedAzimuthParamOid
,	 	 AntCommandedElevation
,	 	 antCommandedElevationParamOid
,	 	 AntContrAzimuth
,	 	 antContrAzimuthParamOid
,	 	 AntContrElevation
,	 	 antContrElevationParamOid
,	 	 AntContrAzimuthRate
,	 	 antContrAzimuthRateParamOid
,	 	 AntContrElevationRate
,	 	 antContrElevationRateParamOid
,	 	 AntAzimuthResidual
,	 	 antAzimuthResidualParamOid
,	 	 AntElevationResidual
,	 	 antElevationResidualParamOid
,	 	 AntAzimuthAberration
,	 	 antAzimuthAberrationParamOid
,	 	 AntElevationAberration
,	 	 antElevationAberrationParamOid
,	 	 AntPointingMode
,	 	 antPointingModeParamOid
,	 	 AntClosedLoopConfiguration
,	 	 antClosedLoopConfigurationParamOid
,	 	 AntTrackingRxMode
,	 	 antTrackingRxModeParamOid
,	 	 AntTrackingSignalPolarization
,	 	 antTrackingSignalPolarizationParamOid
,	 	 AntTrackingRxInpLevel
,	 	 antTrackingRxInpLevelParamOid
,	 	 AntTrackingRxNominalFreq
,	 	 antTrackingRxNominalFreqParamOid
,	 	 AntTrackingRxFreqSearchRange
,	 	 antTrackingRxFreqSearchRangeParamOid
,	 	 AntTrackingRxPredictMode
,	 	 antTrackingRxPredictModeParamOid
,	 	 AntTrackingRxLoopBwdth
,	 	 antTrackingRxLoopBwdthParamOid
,	 	 AntTrackingRxOrderOfLoop
,	 	 antTrackingRxOrderOfLoopParamOid
,	 	 AntTrackingRxLockStat
,	 	 antTrackingRxLockStatParamOid
,	 	 AntWindIntegrationTime
,	 	 antWindIntegrationTimeParamOid
,	 	 AntMeanWindSpeed
,	 	 antMeanWindSpeedParamOid
,	 	 AntPeakWindSpeed
,	 	 antPeakWindSpeedParamOid
,	 	 AntWindDirection
,	 	 antWindDirectionParamOid
,	 	 AntAccumulatedPrecipitation
,	 	 antAccumulatedPrecipitationParamOid
,	 	 AntPrecipitationRate
,	 	 antPrecipitationRateParamOid
,	 	 AntRelativeHumidity
,	 	 antRelativeHumidityParamOid
,	 	 AntAtmosphericPressure
,	 	 antAtmosphericPressureParamOid
,	 	 AntAmbientTemperature
,	 	 antAmbientTemperatureParamOid
,	 	 antResourceStatChangeEventOid
,	 	 AntResourceStatChangeEventValue
,	 	 antResourceStatChangeEventValueValueOid
,	 	 antTrackingRxLockStatChangeEventOid
,	 	 AntTrackingRxLockStatChangeEventValue
,	 	 antTrackingRxLockStatChangeEventValueValueOid
,	 	 antWindSpeedWarningEventOid
,	 	 AntWindSpeedWarningEventValue
,	 	 antWindSpeedWarningEventValueValueOid
,	 	 antSetContrParamsDirectiveOid
,	 	 AntContrParamIdsAndValues
,	 	 antContrParamIdsAndValuesQualifierOid
,	 	 antArrayFrOid
,	 	 ccsds401SpaceLinkCarrierXmitFrOid
,	 	 Ccsds401CarrierXmitResourceStat
,	 	 ccsds401CarrierXmitResourceStatParamOid
,	 	 Ccsds401CarrierXmitPhysChnlName
,	 	 ccsds401CarrierXmitPhysChnlNameParamOid
,	 	 Ccsds401CarrierXmitStat
,	 	 ccsds401CarrierXmitStatParamOid
,	 	 Ccsds401CarrierXmitEirp
,	 	 ccsds401CarrierXmitEirpParamOid
,	 	 Ccsds401CarrierXmitPolarization
,	 	 ccsds401CarrierXmitPolarizationParamOid
,	 	 Ccsds401CarrierXmitActualCarrierFreq
,	 	 ccsds401CarrierXmitActualCarrierFreqParamOid
,	 	 Ccsds401CarrierXmitNominalCarrierFreq
,	 	 ccsds401CarrierXmitNominalCarrierFreqParamOid
,	 	 Ccsds401CarrierXmitReferenceFreqLock
,	 	 ccsds401CarrierXmitReferenceFreqLockParamOid
,	 	 Ccsds401CarrierXmitSweepProcStat
,	 	 ccsds401CarrierXmitSweepProcStatParamOid
,	 	 Ccsds401CarrierXmitSweepProfile
,	 	 ccsds401CarrierXmitSweepProfileParamOid
,	 	 Ccsds401CarrierXmitMod
,	 	 ccsds401CarrierXmitModParamOid
,	 	 Ccsds401CarrierXmitModInpStat
,	 	 ccsds401CarrierXmitModInpStatParamOid
,	 	 Ccsds401CarrierXmitTcPriority
,	 	 ccsds401CarrierXmitTcPriorityParamOid
,	 	 Ccsds401CarrierXmitSymbolStreamModType
,	 	 ccsds401CarrierXmitSymbolStreamModTypeParamOid
,	 	 Ccsds401CarrierXmitRngModIndex
,	 	 ccsds401CarrierXmitRngModIndexParamOid
,	 	 Ccsds401CarrierXmitSubcarrierFreq
,	 	 ccsds401CarrierXmitSubcarrierFreqParamOid
,	 	 Ccsds401CarrierXmitSubcarrierMod
,	 	 ccsds401CarrierXmitSubcarrierModParamOid
,	 	 Ccsds401CarrierXmitSymbolRate
,	 	 ccsds401CarrierXmitSymbolRateParamOid
,	 	 ccsds401CarrierXmitResourceStatChangeEventOid
,	 	 Ccsds401CarrierXmitResourceStatChangeEventValue
,	 	 ccsds401CarrierXmitResourceStatChangeEventValueValueOid
,	 	 ccsds401CarrierXmitSetContrParamsDirectiveOid
,	 	 Ccsds401CarrierXmitContrParamIdsAndValues
,	 	 ccsds401CarrierXmitContrParamIdsAndValuesQualifierOid
,	 	 rngXmitFrOid
,	 	 RngXmitResourceStat
,	 	 rngXmitResourceStatParamOid
,	 	 RngXmitMod
,	 	 rngXmitModParamOid
,	 	 RngXmitRngType
,	 	 rngXmitRngTypeParamOid
,	 	 RngXmitPnChipRate
,	 	 rngXmitPnChipRateParamOid
,	 	 rngXmitResourceStatChangeEventOid
,	 	 RngXmitResourceStatChangeEventValue
,	 	 rngXmitResourceStatChangeEventValueValueOid
,	 	 rngXmitSetContrParamsDirectiveOid
,	 	 RngXmitContrParamIdsAndValues
,	 	 rngXmitContrParamIdsAndValuesQualifierOid
,	 	 ccsds401SpaceLinkCarrierRcptFrOid
,	 	 Ccsds401CarrierRcptResourceStat
,	 	 ccsds401CarrierRcptResourceStatParamOid
,	 	 Ccsds401CarrierRcptPhysChnlName
,	 	 ccsds401CarrierRcptPhysChnlNameParamOid
,	 	 Ccsds401CarrierRcptModType
,	 	 ccsds401CarrierRcptModTypeParamOid
,	 	 Ccsds401CarrierRcptPolarization
,	 	 ccsds401CarrierRcptPolarizationParamOid
,	 	 Ccsds401CarrierRcptPolarizationAngle
,	 	 ccsds401CarrierRcptPolarizationAngleParamOid
,	 	 Ccsds401CarrierRcptExpectedSignalLevel
,	 	 ccsds401CarrierRcptExpectedSignalLevelParamOid
,	 	 Ccsds401CarrierRcptSignalLevelResidual
,	 	 ccsds401CarrierRcptSignalLevelResidualParamOid
,	 	 Ccsds401CarrierRcptSystemNoiseTemperature
,	 	 ccsds401CarrierRcptSystemNoiseTemperatureParamOid
,	 	 Ccsds401CarrierRcptNominalFreq
,	 	 ccsds401CarrierRcptNominalFreqParamOid
,	 	 Ccsds401CarrierRcptFreqSearchRange
,	 	 ccsds401CarrierRcptFreqSearchRangeParamOid
,	 	 Ccsds401CarrierRcptPredictMode
,	 	 ccsds401CarrierRcptPredictModeParamOid
,	 	 Ccsds401CarrierRcptTrackingLoopBwdth
,	 	 ccsds401CarrierRcptTrackingLoopBwdthParamOid
,	 	 Ccsds401CarrierRcptOrderOfLoop
,	 	 ccsds401CarrierRcptOrderOfLoopParamOid
,	 	 Ccsds401CarrierRcptLockStat
,	 	 ccsds401CarrierRcptLockStatParamOid
,	 	 Ccsds401CarrierRcptCarrierLoopSnr
,	 	 ccsds401CarrierRcptCarrierLoopSnrParamOid
,	 	 Ccsds401CarrierRcptCarrierLoopMeanPhaseError
,	 	 ccsds401CarrierRcptCarrierLoopMeanPhaseErrorParamOid
,	 	 Ccsds401CarrierRcptActualFreq
,	 	 ccsds401CarrierRcptActualFreqParamOid
,	 	 Ccsds401CarrierRcptFreqOffset
,	 	 ccsds401CarrierRcptFreqOffsetParamOid
,	 	 Ccsds401CarrierRcptDopplerStdDeviation
,	 	 ccsds401CarrierRcptDopplerStdDeviationParamOid
,	 	 Ccsds401CarrierRcptBestLockFreq
,	 	 ccsds401CarrierRcptBestLockFreqParamOid
,	 	 Ccsds401CarrierRcptNominallSubcarrierFreq
,	 	 ccsds401CarrierRcptNominallSubcarrierFreqParamOid
,	 	 Ccsds401CarrierRcptActualSubcarrierFreq
,	 	 ccsds401CarrierRcptActualSubcarrierFreqParamOid
,	 	 Ccsds401CarrierRcptSubcarrierDemodLoopBwdth
,	 	 ccsds401CarrierRcptSubcarrierDemodLoopBwdthParamOid
,	 	 Ccsds401CarrierRcptSubcarrierLoopMeanPhaseError
,	 	 ccsds401CarrierRcptSubcarrierLoopMeanPhaseErrorParamOid
,	 	 Ccsds401CarrierRcptSubcarrierLevelEstimate
,	 	 ccsds401CarrierRcptSubcarrierLevelEstimateParamOid
,	 	 Ccsds401CarrierRcptNominalSymbolRate
,	 	 ccsds401CarrierRcptNominalSymbolRateParamOid
,	 	 Ccsds401CarrierRcptActualSymbolRate
,	 	 ccsds401CarrierRcptActualSymbolRateParamOid
,	 	 Ccsds401CarrierRcptSymbolSynchronizerLoopBwdth
,	 	 ccsds401CarrierRcptSymbolSynchronizerLoopBwdthParamOid
,	 	 Ccsds401CarrierRcptSymbolLoopMeanPhaseError
,	 	 ccsds401CarrierRcptSymbolLoopMeanPhaseErrorParamOid
,	 	 Ccsds401CarrierRcptExpectedEsOverNo
,	 	 ccsds401CarrierRcptExpectedEsOverNoParamOid
,	 	 Ccsds401CarrierRcptEsOverNoResidualAndSoftSymbolDistribution
,	 	 ccsds401CarrierRcptEsOverNoResidualAndSoftSymbolDistributionParamOid
,	 	 ccsds401CarrierRcptResourceStatChangeEventOid
,	 	 Ccsds401CarrierRcptResourceStatChangeEventValue
,	 	 ccsds401CarrierRcptResourceStatChangeEventValueValueOid
,	 	 ccsds401CarrierRcptLockStatChangeEventOid
,	 	 Ccsds401CarrierRcptLockStatChangeEventValue
,	 	 ccsds401CarrierRcptLockStatChangeEventValueValueOid
,	 	 ccsds401CarrierRcptSetContrParamsDirectiveOid
,	 	 Ccsds401SpaceLinkCarrierRcptContrParamIdsAndValues
,	 	 ccsds401SpaceLinkCarrierRcptContrParamIdsAndValuesQualifierOid
,	 	 rngAndDopplerExtractionFrOid
,	 	 RngAndDopplerExtractionResourceStat
,	 	 rngAndDopplerExtractionResourceStatParamOid
,	 	 RngAndDopplerExtractionPresteering
,	 	 rngAndDopplerExtractionPresteeringParamOid
,	 	 RngAndDopplerExtractionRngPowerOverNoResidual
,	 	 rngAndDopplerExtractionRngPowerOverNoResidualParamOid
,	 	 RngAndDopplerExtractionRngLoopBwdth
,	 	 rngAndDopplerExtractionRngLoopBwdthParamOid
,	 	 RngAndDopplerExtractionPredictedRngLoopSnr
,	 	 rngAndDopplerExtractionPredictedRngLoopSnrParamOid
,	 	 RngAndDopplerExtractionRngSignalAcquisitionProbability
,	 	 rngAndDopplerExtractionRngSignalAcquisitionProbabilityParamOid
,	 	 RngAndDopplerExtractionOpenLoopTime
,	 	 rngAndDopplerExtractionOpenLoopTimeParamOid
,	 	 RngAndDopplerExtractionLoopSettlingTime
,	 	 rngAndDopplerExtractionLoopSettlingTimeParamOid
,	 	 RngAndDopplerExtractionLoopLockStat
,	 	 rngAndDopplerExtractionLoopLockStatParamOid
,	 	 RngAndDopplerExtractionRngToCarrierPowerRatio
,	 	 rngAndDopplerExtractionRngToCarrierPowerRatioParamOid
,	 	 RngAndDopplerExtractionExpectedRngModIndex
,	 	 rngAndDopplerExtractionExpectedRngModIndexParamOid
,	 	 RngAndDopplerExtractionToneIntegrationTime
,	 	 rngAndDopplerExtractionToneIntegrationTimeParamOid
,	 	 RngAndDopplerExtractionPnCodeIntegrationTime
,	 	 rngAndDopplerExtractionPnCodeIntegrationTimeParamOid
,	 	 RngAndDopplerExtractionCodeNumberCorrelated
,	 	 rngAndDopplerExtractionCodeNumberCorrelatedParamOid
,	 	 RngAndDopplerExtractionAmbiguityResolved
,	 	 rngAndDopplerExtractionAmbiguityResolvedParamOid
,	 	 RngAndDopplerExtractionSpacecraftTransponderMode
,	 	 rngAndDopplerExtractionSpacecraftTransponderModeParamOid
,	 	 RngAndDopplerExtractionExpectedSpacecraftPnAcqDuration
,	 	 rngAndDopplerExtractionExpectedSpacecraftPnAcqDurationParamOid
,	 	 RngAndDopplerExtractionRngMeasurementSamplingRate
,	 	 rngAndDopplerExtractionRngMeasurementSamplingRateParamOid
,	 	 RngAndDopplerExtractionDopplerMeasurementSamplingRate
,	 	 rngAndDopplerExtractionDopplerMeasurementSamplingRateParamOid
,	 	 RngAndDopplerExtractionDataCollection
,	 	 rngAndDopplerExtractionDataCollectionParamOid
,	 	 RngAndDopplerExtractionObservableAndResidual
,	 	 rngAndDopplerExtractionObservableAndResidualParamOid
,	 	 RngAndDopplerExtractionObservablesCount
,	 	 rngAndDopplerExtractionObservablesCountParamOid
,	 	 rngAndDopplerExtractionResourceStatChangeEventOid
,	 	 RngAndDopplerExtractionResourceStatChangeEventValue
,	 	 rngAndDopplerExtractionResourceStatChangeEventValueValueOid
,	 	 rngAndDopplerExtractionStatChangeEventOid
,	 	 RngAndDopplerExtractionStatChangeEventValue
,	 	 rngAndDopplerExtractionStatChangeEventValueValueOid
,	 	 rngAndDopplerExtractionSetContrParamsDirectiveOid
,	 	 RngAndDopplerExtractionContrParamIdsAndValues
,	 	 rngAndDopplerExtractionContrParamIdsAndValuesQualifierOid
,	 	 tcPlopSyncAndChnlEncodeFrOid
,	 	 TcPlopSyncResourceStat
,	 	 tcPlopSyncResourceStatParamOid
,	 	 TcPlopSyncMaxCltuLength
,	 	 tcPlopSyncMaxCltuLengthParamOid
,	 	 TcPlopSyncMaxNumberOfFramesPerCltu
,	 	 tcPlopSyncMaxNumberOfFramesPerCltuParamOid
,	 	 TcPlopSyncEncodeType
,	 	 tcPlopSyncEncodeTypeParamOid
,	 	 TcPlopSyncMaxCltuRepetitions
,	 	 tcPlopSyncMaxCltuRepetitionsParamOid
,	 	 TcPlopSyncPlop
,	 	 tcPlopSyncPlopParamOid
,	 	 TcPlopSyncAcqAndIdlePattern
,	 	 tcPlopSyncAcqAndIdlePatternParamOid
,	 	 TcPlopSyncMinDelayTime
,	 	 tcPlopSyncMinDelayTimeParamOid
,	 	 TcPlopSyncTcLinkStat
,	 	 tcPlopSyncTcLinkStatParamOid
,	 	 TcPlopSyncClcwEvaluation
,	 	 tcPlopSyncClcwEvaluationParamOid
,	 	 tcPlopSyncResourceStatChangeEventOid
,	 	 TcPlopSyncResourceStatChangeEventValue
,	 	 tcPlopSyncResourceStatChangeEventValueValueOid
,	 	 tcPlopSyncTcLinkStatChangeEventOid
,	 	 TcPlopSyncTcLinkStatChangeEventValue
,	 	 tcPlopSyncTcLinkStatChangeEventValueValueOid
,	 	 tcPlopSyncDataUnitProcessingCompletedEventOid
,	 	 TcPlopSyncDataUnitProcessingCompletedEventValue
,	 	 tcPlopSyncDataUnitProcessingCompletedEventValueValueOid
,	 	 tcPlopSyncSetContrParamsDirectiveOid
,	 	 TcPlopSyncContrParamIdsAndValues
,	 	 tcPlopSyncContrParamIdsAndValuesQualifierOid
,	 	 tcPlopSyncDiscardDataUnitsDirectiveOid
,	 	 TcPlopSyncFrAndServiceInstanceId
,	 	 tcPlopSyncFrAndServiceInstanceIdQualifierOid
,	 	 flfSyncChnlEncodeAndOidGenFrOid
,	 	 FlfSyncEncResourceStat
,	 	 flfSyncEncResourceStatParamOid
,	 	 FlfSyncEncSlpduLength
,	 	 flfSyncEncSlpduLengthParamOid
,	 	 FlfSyncEncCodingSelection
,	 	 flfSyncEncCodingSelectionParamOid
,	 	 flfSyncEncResourceStatChangeEventOid
,	 	 FlfSyncEncResourceStatValue
,	 	 flfSyncEncResourceStatValueValueOid
,	 	 flfSyncEncDataUnitProcessingCompletedEventOid
,	 	 FlfSyncEncDataUnitProcessingCompletedValue
,	 	 flfSyncEncDataUnitProcessingCompletedValueValueOid
,	 	 flfSyncEncSetContrParamsDirectiveOid
,	 	 FlfSyncEncContrParamIdsAndValues
,	 	 flfSyncEncContrParamIdsAndValuesQualifierOid
,	 	 flfSyncEncDiscardDataUnitsDirectiveOid
,	 	 FlfSyncEncDiscardDataUnitsSvcInstanceId
,	 	 flfSyncEncDiscardDataUnitsSvcInstanceIdQualifierOid
,	 	 flfSyncAndChnlDecodeFrOid
,	 	 FlfSyncDecResourceStat
,	 	 flfSyncDecResourceStatParamOid
,	 	 FlfSyncDecAsmConfig
,	 	 flfSyncDecAsmConfigParamOid
,	 	 FlfSyncDecAsmCorrelationError
,	 	 flfSyncDecAsmCorrelationErrorParamOid
,	 	 FlfSyncDecFrameSyncLockStat
,	 	 flfSyncDecFrameSyncLockStatParamOid
,	 	 FlfSyncDecSymbolInversion
,	 	 flfSyncDecSymbolInversionParamOid
,	 	 FlfSyncDecFrameErrorRate
,	 	 flfSyncDecFrameErrorRateParamOid
,	 	 FlfSyncDecNumberOfRsErrorsCorrected
,	 	 flfSyncDecNumberOfRsErrorsCorrectedParamOid
,	 	 FlfSyncDecErtAnnotationLockedToReference
,	 	 flfSyncDecErtAnnotationLockedToReferenceParamOid
,	 	 FlfSyncDecCaduLength
,	 	 flfSyncDecCaduLengthParamOid
,	 	 FlfSyncDecDerandomization
,	 	 flfSyncDecDerandomizationParamOid
,	 	 FlfSyncDecDecode
,	 	 flfSyncDecDecodeParamOid
,	 	 FlfSyncDecFecfPresent
,	 	 flfSyncDecFecfPresentParamOid
,	 	 FlfSyncDecDecodeQualityIndications
,	 	 flfSyncDecDecodeQualityIndicationsParamOid
,	 	 flfSyncDecResourceStatChangeEventOid
,	 	 FlfSyncDecResourceStatChangeEventValue
,	 	 flfSyncDecResourceStatChangeEventValueValueOid
,	 	 flfSyncDecFrameSyncLockStatChangeEventOid
,	 	 FlfSyncDecFrameSyncLockStatChangeEventValue
,	 	 flfSyncDecFrameSyncLockStatChangeEventValueValueOid
,	 	 flfSyncDecSetContrParamsDirectiveOid
,	 	 FlfSyncDecContrParamIdsAndValues
,	 	 flfSyncDecContrParamIdsAndValuesQualifierOid
,	 	 tcMcMuxFrOid
,	 	 TcMcMuxResourceStat
,	 	 tcMcMuxResourceStatParamOid
,	 	 TcMcMuxMaxNumberOfFramesPerCltu
,	 	 tcMcMuxMaxNumberOfFramesPerCltuParamOid
,	 	 TcMcMuxMaxFrameLength
,	 	 tcMcMuxMaxFrameLengthParamOid
,	 	 TcMcMuxContr
,	 	 tcMcMuxContrParamOid
,	 	 TcMcMuxPresenceOfFec
,	 	 tcMcMuxPresenceOfFecParamOid
,	 	 tcMcMuxResourceStatChangeEventOid
,	 	 TcMcMuxResourceStatChangeEventValue
,	 	 tcMcMuxResourceStatChangeEventValueValueOid
,	 	 tcMcMuxSetContrParamsDirectiveOid
,	 	 TcMcMuxContrParamIdsAndValues
,	 	 tcMcMuxContrParamIdsAndValuesQualifierOid
,	 	 tcMcMuxDiscardDataUnitsDirectiveOid
,	 	 TcMcMuxDiscardDataUnitsQualifier
,	 	 tcMcMuxDiscardDataUnitsQualifierQualifierOid
,	 	 tcVcMuxFrOid
,	 	 TcVcMuxResourceStat
,	 	 tcVcMuxResourceStatParamOid
,	 	 TcVcMuxMaxFrameLength
,	 	 tcVcMuxMaxFrameLengthParamOid
,	 	 TcVcMuxAdFrameRepetitions
,	 	 tcVcMuxAdFrameRepetitionsParamOid
,	 	 TcVcMuxBcFrameRepetitions
,	 	 tcVcMuxBcFrameRepetitionsParamOid
,	 	 TcVcMuxMc
,	 	 tcVcMuxMcParamOid
,	 	 TcVcMuxContr
,	 	 tcVcMuxContrParamOid
,	 	 tcVcMuxResourceStatChangeEventOid
,	 	 TcVcMuxResourceStatChangeEventValue
,	 	 tcVcMuxResourceStatChangeEventValueValueOid
,	 	 tcVcMuxSetContrParamsDirectiveOid
,	 	 TcVcMuxContrParamIdsAndValues
,	 	 tcVcMuxContrParamIdsAndValuesQualifierOid
,	 	 tcVcMuxDiscardDataUnitsDirectiveOid
,	 	 TcVcMuxDiscardDataUnitsQualifier
,	 	 tcVcMuxDiscardDataUnitsQualifierQualifierOid
,	 	 tcEncapVcPktProcVcGenFrOid
,	 	 tcEncapSetContrParamsDirectiveOid
,	 	 tcMapMuxFrOid
,	 	 tcEncapMapPktProcessingFrOid
,	 	 aosMcMuxFrOid
,	 	 AosMcMuxResourceStat
,	 	 aosMcMuxResourceStatParamOid
,	 	 AosMcMuxContr
,	 	 aosMcMuxContrParamOid
,	 	 AosMcMuxPresenceOfFrameHeaderErrorContr
,	 	 aosMcMuxPresenceOfFrameHeaderErrorContrParamOid
,	 	 AosMcMuxPresenceOfFrameErrorContr
,	 	 aosMcMuxPresenceOfFrameErrorContrParamOid
,	 	 aosMcMuxResourceStatChangeEventOid
,	 	 AosMcMuxResourceStatValue
,	 	 aosMcMuxResourceStatValueValueOid
,	 	 aosMcMuxDataUnitProcessingCompletedEventOid
,	 	 AosMcMuxDataUnitProcessingCompletedValue
,	 	 aosMcMuxDataUnitProcessingCompletedValueValueOid
,	 	 aosMcMuxSetContrParamsDirectiveOid
,	 	 AosMcMuxContrParamIdsAndValues
,	 	 aosMcMuxContrParamIdsAndValuesQualifierOid
,	 	 aosMcMuxDiscardDataUnitsDirectiveOid
,	 	 AosMcMuxDiscardDataUnitsSvcInstanceId
,	 	 aosMcMuxDiscardDataUnitsSvcInstanceIdQualifierOid
,	 	 aosVcMuxFrOid
,	 	 AosVcMuxResourceStat
,	 	 aosVcMuxResourceStatParamOid
,	 	 AosVcMuxMc
,	 	 aosVcMuxMcParamOid
,	 	 AosVcMuxContr
,	 	 aosVcMuxContrParamOid
,	 	 aosVcMuxResourceStatChangeEventOid
,	 	 AosVcMuxResourceStatValue
,	 	 aosVcMuxResourceStatValueValueOid
,	 	 aosVcMuxDataUnitProcessingCompletedEventOid
,	 	 AosVcMuxDataUnitProcessingCompletedValue
,	 	 aosVcMuxDataUnitProcessingCompletedValueValueOid
,	 	 aosVcMuxSetContrParamsDirectiveOid
,	 	 AosVcMuxContrParamIdsAndValues
,	 	 aosVcMuxContrParamIdsAndValuesQualifierOid
,	 	 aosVcMuxDiscardDataUnitsDirectiveOid
,	 	 AosVcMuxDiscardDataUnitsSvcInstanceId
,	 	 aosVcMuxDiscardDataUnitsSvcInstanceIdQualifierOid
,	 	 aosEncapPktProcAndVcGenFrOid
,	 	 vlfUslpMcMuxFrOid
,	 	 vlfUslpVcMuxFrOid
,	 	 vlfUslpVcGenFrOid
,	 	 uslpMapMuxFrOid
,	 	 uslpEncapMapPktProcessingFrOid
,	 	 flfUslpMcMuxFrOid
,	 	 FlfUslpMcMuxResourceStat
,	 	 flfUslpMcMuxResourceStatParamOid
,	 	 FlfUslpMcMuxContr
,	 	 flfUslpMcMuxContrParamOid
,	 	 FlfUslpMcMuxFrameErrorContrLength
,	 	 flfUslpMcMuxFrameErrorContrLengthParamOid
,	 	 flfUslpMcMuxDataUnitProcessingCompletedEventOid
,	 	 FlfUslpMcMuxDataUnitProcessingCompletedValue
,	 	 flfUslpMcMuxDataUnitProcessingCompletedValueValueOid
,	 	 flfUslpMcMuxResourceStatChangeEventOid
,	 	 FlfUslpMcMuxResourceStatValue
,	 	 flfUslpMcMuxResourceStatValueValueOid
,	 	 flfUslpMcMuxSetContrParamsDirectiveOid
,	 	 FlfUslpMcMuxSetContrParamIdsAndValues
,	 	 flfUslpMcMuxSetContrParamIdsAndValuesQualifierOid
,	 	 flfUslpMcMuxDiscardDataUnitsDirectiveOid
,	 	 FlfUslpMcMuxDiscardDataUnitsSvcInstanceId
,	 	 flfUslpMcMuxDiscardDataUnitsSvcInstanceIdQualifierOid
,	 	 flfUslpVcMuxFrOid
,	 	 FlfUslpVcMuxResourceStat
,	 	 flfUslpVcMuxResourceStatParamOid
,	 	 FlfUslpVcMuxMc
,	 	 flfUslpVcMuxMcParamOid
,	 	 FlfUslpVcMuxContr
,	 	 flfUslpVcMuxContrParamOid
,	 	 flfUslpVcMuxResourceStatChangeEventOid
,	 	 FlfUslpVcMuxResourceStatValue
,	 	 flfUslpVcMuxResourceStatValueValueOid
,	 	 flfUslpVcMuxDataUnitProcessingCompletedEventOid
,	 	 Flf-UslpVcMuxDataUnitProcessingCompletedValue
,	 	 flf-UslpVcMuxDataUnitProcessingCompletedValueValueOid
,	 	 flfUslpVcMuxSetContrParamsDirectiveOid
,	 	 FlfUslpVcMuxContrParamIdsAndValues
,	 	 flfUslpVcMuxContrParamIdsAndValuesQualifierOid
,	 	 flfUslpVcMuxDiscardDataUnitsDirectiveOid
,	 	 FlfUslpVcMuxDiscardDataUnitsSvcInstanceId
,	 	 flfUslpVcMuxDiscardDataUnitsSvcInstanceIdQualifierOid
,	 	 flfUslpVcGenFrOid
,	 	 flfUslpMapMuxFrOid
,	 	 flfUslpEncapMapPktProcessingFrOid
,	 	 tmAosMcDemuxFrOid
,	 	 TmAosMcDemuxResourceStat
,	 	 tmAosMcDemuxResourceStatParamOid
,	 	 TmAosMcDemuxMcIds
,	 	 tmAosMcDemuxMcIdsParamOid
,	 	 TmAosMcDemuxClcwExtraction
,	 	 tmAosMcDemuxClcwExtractionParamOid
,	 	 tmAosMcDemuxResourceStatChangeEventOid
,	 	 TmAosMcDemuxResourceStatChangeEventValue
,	 	 tmAosMcDemuxResourceStatChangeEventValueValueOid
,	 	 tmAosMcDemuxSetContrParamsDirectiveOid
,	 	 TmAosMcDemuxContrParamIdsAndValues
,	 	 tmAosMcDemuxContrParamIdsAndValuesQualifierOid
,	 	 tmAosVcDemuxFrOid
,	 	 TmAosVcDemuxResourceStat
,	 	 tmAosVcDemuxResourceStatParamOid
,	 	 TmAosVcDemuxVcId
,	 	 tmAosVcDemuxVcIdParamOid
,	 	 TmAosVcDemuxClcwExtraction
,	 	 tmAosVcDemuxClcwExtractionParamOid
,	 	 TmAosVcDemuxGvcid
,	 	 tmAosVcDemuxGvcidParamOid
,	 	 tmAosVcDemuxResourceStatChangeEventOid
,	 	 TmAosVcDemuxResourceStatChangeEventValue
,	 	 tmAosVcDemuxResourceStatChangeEventValueValueOid
,	 	 tmAosVcDemuxSetContrParamsDirectiveOid
,	 	 TmAosVcDemuxContrParamIdsAndValues
,	 	 tmAosVcDemuxContrParamIdsAndValuesQualifierOid
,	 	 tmAosPktExtractDeencapFrOid
,	 	 TmAosSpacePktApidSet
,	 	 tmAosSpacePktApidSetParamOid
,	 	 frameDataSinkFrOid
,	 	 FrameDataSinkResourceStat
,	 	 frameDataSinkResourceStatParamOid
,	 	 FrameDataSinkStorageSelection
,	 	 frameDataSinkStorageSelectionParamOid
,	 	 frameDataSinkResourceStatChangeEventOid
,	 	 FrameDataSinkResourceStatChangeValue
,	 	 frameDataSinkResourceStatChangeValueValueOid
,	 	 frameDataSinkSetContrParamsDirectiveOid
,	 	 FrameDataSinkContrParamIdsAndValues
,	 	 frameDataSinkContrParamIdsAndValuesQualifierOid
,	 	 cfdpEntityFrOid
,	 	 CfdpLocalEntityResourceStat
,	 	 cfdpLocalEntityResourceStatParamOid
,	 	 CfdpLocalEntityId
,	 	 cfdpLocalEntityIdParamOid
,	 	 CfdpRemoteEntityConfiguration
,	 	 cfdpRemoteEntityConfigurationParamOid
,	 	 CfdpLocalEntityConfiguration
,	 	 cfdpLocalEntityConfigurationParamOid
,	 	 cfdpTransactionIndicationEventOid
,	 	 CfdpTransactionTransactionId
,	 	 cfdpTransactionTransactionIdValueOid
,	 	 cfdpEofSentIndicationEventOid
,	 	 CfdpEofSentTransactionId
,	 	 cfdpEofSentTransactionIdValueOid
,	 	 cfdpTransactionFinishedIndicationEventOid
,	 	 CfdpFinishedTransaction
,	 	 cfdpFinishedTransactionValueOid
,	 	 cfdpMetadataRcvdIndicationEventOid
,	 	 CfdpMetadataIndication
,	 	 cfdpMetadataIndicationValueOid
,	 	 cfdpFileSegmentRcvdIndicationEventOid
,	 	 CfdpFileSegmentIndicationValue
,	 	 cfdpFileSegmentIndicationValueValueOid
,	 	 cfdpReportRcvdIndicationEventOid
,	 	 CfdpReportIndication
,	 	 cfdpReportIndicationValueOid
,	 	 cfdpSuspendedIndicationEventOid
,	 	 CfdpSuspendedIndication
,	 	 cfdpSuspendedIndicationValueOid
,	 	 cfdpResumedIndicationEventOid
,	 	 CfdpResumedIndication
,	 	 cfdpResumedIndicationValueOid
,	 	 cfdpFaultIndicationEventOid
,	 	 CfdpFaultIndication
,	 	 cfdpFaultIndicationValueOid
,	 	 cfdpAbandonedIndicationEventOid
,	 	 CfdpAbandonedIndication
,	 	 cfdpAbandonedIndicationValueOid
,	 	 cfdpEofRcvdIndicationEventOid
,	 	 CfdpEofRcvdTransactionId
,	 	 cfdpEofRcvdTransactionIdValueOid
,	 	 cfdpTransferConsignedIndicationEventOid
,	 	 CfdpConsignedTransactionId
,	 	 cfdpConsignedTransactionIdValueOid
,	 	 cfdpPutRequestDirectiveOid
,	 	 CfdpPutRequest
,	 	 cfdpPutRequestQualifierOid
,	 	 cfdpReportRequestDirectiveOid
,	 	 CfdpReportRequestTransactionId
,	 	 cfdpReportRequestTransactionIdQualifierOid
,	 	 cfdpCancelRequestDirectiveOid
,	 	 CfdpCancelRequestTransactionId
,	 	 cfdpCancelRequestTransactionIdQualifierOid
,	 	 cfdpSuspendRequestDirectiveOid
,	 	 CfdpSuspendTransactionId
,	 	 cfdpSuspendTransactionIdQualifierOid
,	 	 cfdpResumeRequestDirectiveOid
,	 	 CfdpResumeTransactionId
,	 	 cfdpResumeTransactionIdQualifierOid
,	 	 fwdFileSvcProdFrOid
,	 	 rtnFileSvcProdFrOid
,	 	 cfdpSendEntityFrOid
,	 	 cfdpRcvEntityFrOid
,	 	 tdmSegmentGenFrOid
,	 	 TdmSegGenResourceStat
,	 	 tdmSegGenResourceStatParamOid
,	 	 TdmSegGenCarrierPowerPathTable
,	 	 tdmSegGenCarrierPowerPathTableParamOid
,	 	 TdmSegGenPcOverN0PathTable
,	 	 tdmSegGenPcOverN0PathTableParamOid
,	 	 TdmSegGenPrOverNoPathTable
,	 	 tdmSegGenPrOverNoPathTableParamOid
,	 	 TdmSegGenDoppInstPathTable
,	 	 tdmSegGenDoppInstPathTableParamOid
,	 	 TdmSegGenDoppIntegPathTable
,	 	 tdmSegGenDoppIntegPathTableParamOid
,	 	 TdmSegGenRangePathTable
,	 	 tdmSegGenRangePathTableParamOid
,	 	 TdmSeqGenRcvFreqPathTable
,	 	 tdmSeqGenRcvFreqPathTableParamOid
,	 	 TdmSegGenXmitFreqPathTable
,	 	 tdmSegGenXmitFreqPathTableParamOid
,	 	 TdmSegGenXmitFreqRatePathTable
,	 	 tdmSegGenXmitFreqRatePathTableParamOid
,	 	 TdmSegGenAntAnglesPathTable
,	 	 tdmSegGenAntAnglesPathTableParamOid
,	 	 tdmSegGenResourceStatChangeEventOid
,	 	 TdmSegGenResourceStatChangeValue
,	 	 tdmSegGenResourceStatChangeValueValueOid
,	 	 tdmSegGenSetContrParamsDirectiveOid
,	 	 TdmSegGenContrParamIdsAndValues
,	 	 tdmSegGenContrParamIdsAndValuesQualifierOid
,	 	 nonValRmDataCollectionFrOid
,	 	 ddorRawDataCollectionFrOid
,	 	 openLoopRxFormatterFrOid
,	 	 offlineFrameBufferFrOid
,	 	 OfflineFrameBufferResourceStat
,	 	 offlineFrameBufferResourceStatParamOid
,	 	 OfflineFrameBufferAllocatedStorage
,	 	 offlineFrameBufferAllocatedStorageParamOid
,	 	 OfflineFrameBufferAvailableStorage
,	 	 offlineFrameBufferAvailableStorageParamOid
,	 	 OfflineFrameBufferUsedStorage
,	 	 offlineFrameBufferUsedStorageParamOid
,	 	 OfflineFrameBufferDataRetentionPolicy
,	 	 offlineFrameBufferDataRetentionPolicyParamOid
,	 	 OfflineFrameBufferPurgePriority
,	 	 offlineFrameBufferPurgePriorityParamOid
,	 	 OfflineFrameBufferPurgeCessationThreshold
,	 	 offlineFrameBufferPurgeCessationThresholdParamOid
,	 	 OfflineFrameBufferPurgeWarningThreshold
,	 	 offlineFrameBufferPurgeWarningThresholdParamOid
,	 	 offlineFrameBufferResourceStatChangeEventOid
,	 	 OfflineFrameBufferResourceStatChangeValue
,	 	 offlineFrameBufferResourceStatChangeValueValueOid
,	 	 offlineFrameBufferPurgeWarningEventOid
,	 	 OfflineFrameBufferPurgeWarningValue
,	 	 offlineFrameBufferPurgeWarningValueValueOid
,	 	 offlineFrameBufferSetContrParamsDirectiveOid
,	 	 OfflineFrameBufferContrParamIdsAndValues
,	 	 offlineFrameBufferContrParamIdsAndValuesQualifierOid
,	 	 tdmRcrdBufferFrOid
,	 	 TdmRcrdBufferResourceStat
,	 	 tdmRcrdBufferResourceStatParamOid
,	 	 TdmRcrdBufferMaxStorageAlloc
,	 	 tdmRcrdBufferMaxStorageAllocParamOid
,	 	 TdmRcrdBufferRetentionPolicy
,	 	 tdmRcrdBufferRetentionPolicyParamOid
,	 	 tdmRcrdBufferResourceStatChangeEventOid
,	 	 TdmRcrdBufferResourceStatChangeValue
,	 	 tdmRcrdBufferResourceStatChangeValueValueOid
,	 	 tdmRcrdBufferSetContrParamsDirectiveOid
,	 	 TdmRcrdBufferContrParamIdsAndValues
,	 	 tdmRcrdBufferContrParamIdsAndValuesQualifierOid
,	 	 nonValRmDataStoreFrOid
,	 	 valRmDataStoreFrOid
,	 	 ddorRawDataStoreFrOid
,	 	 openLoopDataStoreFrOid
,	 	 rtnFileDataStoreFrOid
,	 	 fwdFileDataStoreFrOid
,	 	 fspTsProviderFrOid
,	 	 FspProdStat
,	 	 fspProdStatParamOid
,	 	 FspSvcInstanceId
,	 	 fspSvcInstanceIdParamOid
,	 	 FspSvcInstanceState
,	 	 fspSvcInstanceStateParamOid
,	 	 FspInitiatorId
,	 	 fspInitiatorIdParamOid
,	 	 FspResponderId
,	 	 fspResponderIdParamOid
,	 	 FspResponderPortId
,	 	 fspResponderPortIdParamOid
,	 	 FspRtnTimeoutPeriod
,	 	 fspRtnTimeoutPeriodParamOid
,	 	 FspDeliveryMode
,	 	 fspDeliveryModeParamOid
,	 	 FspRfAvailableRequired
,	 	 fspRfAvailableRequiredParamOid
,	 	 FspBitLockRequired
,	 	 fspBitLockRequiredParamOid
,	 	 FspDirectiveInvocation
,	 	 fspDirectiveInvocationParamOid
,	 	 FspDirectiveInvocationOnline
,	 	 fspDirectiveInvocationOnlineParamOid
,	 	 Fsp-PermittedTransmissionMode
,	 	 fsp-PermittedTransmissionModeParamOid
,	 	 FspApidList
,	 	 fspApidListParamOid
,	 	 FspReportingCycle
,	 	 fspReportingCycleParamOid
,	 	 FspExpectedPktId
,	 	 fspExpectedPktIdParamOid
,	 	 FspExpectedDirectiveId
,	 	 fspExpectedDirectiveIdParamOid
,	 	 FspExpectedEventInvocId
,	 	 fspExpectedEventInvocIdParamOid
,	 	 FspTcMcMuxValidScids
,	 	 fspTcMcMuxValidScidsParamOid
,	 	 FspTcVcMuxValidTcVcIds
,	 	 fspTcVcMuxValidTcVcIdsParamOid
,	 	 fspProdStatChangeEventOid
,	 	 FspProdStatChangeEventValue
,	 	 fspProdStatChangeEventValueValueOid
,	 	 fspProdConfigurationChangeEventOid
,	 	 FspProdConfigurationChangeEventValue
,	 	 fspProdConfigurationChangeEventValueValueOid
,	 	 fCltuTsProviderFrOid
,	 	 FCltuProdStat
,	 	 fCltuProdStatParamOid
,	 	 FCltuSvcInstanceId
,	 	 fCltuSvcInstanceIdParamOid
,	 	 FCltuSvcInstanceState
,	 	 fCltuSvcInstanceStateParamOid
,	 	 FCltuInitiatorId
,	 	 fCltuInitiatorIdParamOid
,	 	 FCltuResponderId
,	 	 fCltuResponderIdParamOid
,	 	 FCltuResponderPortId
,	 	 fCltuResponderPortIdParamOid
,	 	 FCltuRtnTimeoutPeriod
,	 	 fCltuRtnTimeoutPeriodParamOid
,	 	 FCltuDeliveryMode
,	 	 fCltuDeliveryModeParamOid
,	 	 FCltuNotificationMode
,	 	 fCltuNotificationModeParamOid
,	 	 FCltuProtocolAbortMode
,	 	 fCltuProtocolAbortModeParamOid
,	 	 FCltuReportingCycle
,	 	 fCltuReportingCycleParamOid
,	 	 FCltuExpectedCltuId
,	 	 fCltuExpectedCltuIdParamOid
,	 	 FCltuExpectedEventInvocId
,	 	 fCltuExpectedEventInvocIdParamOid
,	 	 FCltuNumberOfCltusReceived
,	 	 fCltuNumberOfCltusReceivedParamOid
,	 	 FCltuNumberOfCltusProcessed
,	 	 fCltuNumberOfCltusProcessedParamOid
,	 	 FCltuNumberOfCltusRadiated
,	 	 fCltuNumberOfCltusRadiatedParamOid
,	 	 fCltuProdStatChangeEventOid
,	 	 FCltuProdStatChangeEventValue
,	 	 fCltuProdStatChangeEventValueValueOid
,	 	 fCltuProdConfigurationChangeEventOid
,	 	 FCltuProdConfigurationChangeEventValue
,	 	 fCltuProdConfigurationChangeEventValueValueOid
,	 	 fCltuSetContrParamsDirectiveOid
,	 	 FCltuContrParamIdsAndValues
,	 	 fCltuContrParamIdsAndValuesQualifierOid
,	 	 fwdFrameCstsProviderFrOid
,	 	 FfSvcProdStat
,	 	 ffSvcProdStatParamOid
,	 	 FfSvcInstanceId
,	 	 ffSvcInstanceIdParamOid
,	 	 FfSvcInstanceState
,	 	 ffSvcInstanceStateParamOid
,	 	 FfInitiatorId
,	 	 ffInitiatorIdParamOid
,	 	 FfResponderId
,	 	 ffResponderIdParamOid
,	 	 FfResponderPortId
,	 	 ffResponderPortIdParamOid
,	 	 FfSvcUserRespondingTimer
,	 	 ffSvcUserRespondingTimerParamOid
,	 	 FfDataProcessingMode
,	 	 ffDataProcessingModeParamOid
,	 	 FfAuthorizedGvcidAndBitMask
,	 	 ffAuthorizedGvcidAndBitMaskParamOid
,	 	 FfMinFrameLength
,	 	 ffMinFrameLengthParamOid
,	 	 FfMaxFrameLength
,	 	 ffMaxFrameLengthParamOid
,	 	 FfInputQueueSize
,	 	 ffInputQueueSizeParamOid
,	 	 FfMinAllowedDeliveryCycle
,	 	 ffMinAllowedDeliveryCycleParamOid
,	 	 FfNamedEventLabelLists
,	 	 ffNamedEventLabelListsParamOid
,	 	 FfMasterThrowEventEnabled
,	 	 ffMasterThrowEventEnabledParamOid
,	 	 FfNamedParamLabelLists
,	 	 ffNamedParamLabelListsParamOid
,	 	 FfNumberDataUnitsRcvd
,	 	 ffNumberDataUnitsRcvdParamOid
,	 	 FfNumberDataUnitsToProcessing
,	 	 ffNumberDataUnitsToProcessingParamOid
,	 	 FfNumberDataUnitsProcessed
,	 	 ffNumberDataUnitsProcessedParamOid
,	 	 ffSvcProdStatChangeEventOid
,	 	 FfSvcProdStatChangeValue
,	 	 ffSvcProdStatChangeValueValueOid
,	 	 ffSvcProdConfgurationChangeEventOid
,	 	 FfSvcProdConfgurationChangeValue
,	 	 ffSvcProdConfgurationChangeValueValueOid
,	 	 rafTsProviderFrOid
,	 	 RafProdStat
,	 	 rafProdStatParamOid
,	 	 RafSvcInstanceId
,	 	 rafSvcInstanceIdParamOid
,	 	 RafSvcInstanceState
,	 	 rafSvcInstanceStateParamOid
,	 	 RafInitiatorId
,	 	 rafInitiatorIdParamOid
,	 	 RafResponderId
,	 	 rafResponderIdParamOid
,	 	 RafResponderPortId
,	 	 rafResponderPortIdParamOid
,	 	 RafRtnTimeoutPeriod
,	 	 rafRtnTimeoutPeriodParamOid
,	 	 RafDeliveryMode
,	 	 rafDeliveryModeParamOid
,	 	 RafLatencyLimit
,	 	 rafLatencyLimitParamOid
,	 	 RafTransferBufferSize
,	 	 rafTransferBufferSizeParamOid
,	 	 RafPermittedFrameQuality
,	 	 rafPermittedFrameQualityParamOid
,	 	 RafRequestedFrameQuality
,	 	 rafRequestedFrameQualityParamOid
,	 	 RafReportingCycle
,	 	 rafReportingCycleParamOid
,	 	 RafNumberOfErrorFreeFramesDelivered
,	 	 rafNumberOfErrorFreeFramesDeliveredParamOid
,	 	 RafNumberOfFramesDelivered
,	 	 rafNumberOfFramesDeliveredParamOid
,	 	 rafProdStatChangeEventOid
,	 	 RafProdStatChangeEventValue
,	 	 rafProdStatChangeEventValueValueOid
,	 	 rafProdConfigurationChangeEventOid
,	 	 RafProdConfigurationChangeEventValue
,	 	 rafProdConfigurationChangeEventValueValueOid
,	 	 rafSetContrParamsDirectiveOid
,	 	 RafContrParamIdsAndValues
,	 	 rafContrParamIdsAndValuesQualifierOid
,	 	 rcfTsProviderFrOid
,	 	 RcfProdStat
,	 	 rcfProdStatParamOid
,	 	 RcfSvcInstanceId
,	 	 rcfSvcInstanceIdParamOid
,	 	 RcfSvcInstanceState
,	 	 rcfSvcInstanceStateParamOid
,	 	 RcfInitiatorId
,	 	 rcfInitiatorIdParamOid
,	 	 RcfResponderId
,	 	 rcfResponderIdParamOid
,	 	 RcfResponderPortId
,	 	 rcfResponderPortIdParamOid
,	 	 RcfRtnTimeoutPeriod
,	 	 rcfRtnTimeoutPeriodParamOid
,	 	 RcfDeliveryMode
,	 	 rcfDeliveryModeParamOid
,	 	 RcfLatencyLimit
,	 	 rcfLatencyLimitParamOid
,	 	 RcfTransferBufferSize
,	 	 rcfTransferBufferSizeParamOid
,	 	 RcfPermittedGvcidSet
,	 	 rcfPermittedGvcidSetParamOid
,	 	 RcfRequestedGvcid
,	 	 rcfRequestedGvcidParamOid
,	 	 RcfReportingCycle
,	 	 rcfReportingCycleParamOid
,	 	 RcfNumberOfFramesDelivered
,	 	 rcfNumberOfFramesDeliveredParamOid
,	 	 rcfProdStatChangeEventOid
,	 	 RcfProdStatChangeEventValue
,	 	 rcfProdStatChangeEventValueValueOid
,	 	 rcfProdConfigurationChangeEventOid
,	 	 RcfProdConfigurationChangeEventValue
,	 	 rcfProdConfigurationChangeEventValueValueOid
,	 	 rcfSetContrParamsDirectiveOid
,	 	 RcfContrParamIdsAndValues
,	 	 rcfContrParamIdsAndValuesQualifierOid
,	 	 rocfTsProviderFrOid
,	 	 RocfProdStat
,	 	 rocfProdStatParamOid
,	 	 RocfSvcInstanceId
,	 	 rocfSvcInstanceIdParamOid
,	 	 RocfSvcInstanceState
,	 	 rocfSvcInstanceStateParamOid
,	 	 RocfInitiatorId
,	 	 rocfInitiatorIdParamOid
,	 	 RocfResponderId
,	 	 rocfResponderIdParamOid
,	 	 RocfResponderPortId
,	 	 rocfResponderPortIdParamOid
,	 	 RocfRtnTimeoutPeriod
,	 	 rocfRtnTimeoutPeriodParamOid
,	 	 RocfDeliveryMode
,	 	 rocfDeliveryModeParamOid
,	 	 RocfLatencyLimit
,	 	 rocfLatencyLimitParamOid
,	 	 RocfTransferBufferSize
,	 	 rocfTransferBufferSizeParamOid
,	 	 RocfPermittedGvcidSet
,	 	 rocfPermittedGvcidSetParamOid
,	 	 RocfRequestedGvcid
,	 	 rocfRequestedGvcidParamOid
,	 	 RocfPermittedContrWordTypeSet
,	 	 rocfPermittedContrWordTypeSetParamOid
,	 	 RocfRequestedContrWordType
,	 	 rocfRequestedContrWordTypeParamOid
,	 	 RocfPermittedTcVcidSet
,	 	 rocfPermittedTcVcidSetParamOid
,	 	 RocfRequestedTcVcid
,	 	 rocfRequestedTcVcidParamOid
,	 	 RocfPermittedUpdateMode
,	 	 rocfPermittedUpdateModeParamOid
,	 	 RocfRequestedUpdateMode
,	 	 rocfRequestedUpdateModeParamOid
,	 	 RocfReportingCycle
,	 	 rocfReportingCycleParamOid
,	 	 RocfNumberOfOcfsDelivered
,	 	 rocfNumberOfOcfsDeliveredParamOid
,	 	 rocfProdStatChangeEventOid
,	 	 RocfProdStatChangeEventValue
,	 	 rocfProdStatChangeEventValueValueOid
,	 	 rocfProdConfigurationChangeEventOid
,	 	 RocfProdConfigurationChangeEventValue
,	 	 rocfProdConfigurationChangeEventValueValueOid
,	 	 rocfSetContrParamsDirectiveOid
,	 	 RocfContrParamIdsAndValues
,	 	 rocfContrParamIdsAndValuesQualifierOid
,	 	 tdCstsProviderFrOid
,	 	 TdProdStat
,	 	 tdProdStatParamOid
,	 	 TdSvcInstanceId
,	 	 tdSvcInstanceIdParamOid
,	 	 TdSvcInstanceState
,	 	 tdSvcInstanceStateParamOid
,	 	 TdInitiatorId
,	 	 tdInitiatorIdParamOid
,	 	 TdResponderId
,	 	 tdResponderIdParamOid
,	 	 TdResponderPortId
,	 	 tdResponderPortIdParamOid
,	 	 TdSvcUserRespTimer
,	 	 tdSvcUserRespTimerParamOid
,	 	 TdDeliveryMode
,	 	 tdDeliveryModeParamOid
,	 	 TdReturnBufferSize
,	 	 tdReturnBufferSizeParamOid
,	 	 TdDeliveryLatencyLimit
,	 	 tdDeliveryLatencyLimitParamOid
,	 	 TdNamedLabelLists
,	 	 tdNamedLabelListsParamOid
,	 	 TdPathList
,	 	 tdPathListParamOid
,	 	 tdProdStatChangeEventOid
,	 	 TdProdStatChangeEventValue
,	 	 tdProdStatChangeEventValueValueOid
,	 	 tdProdConfigurationChangeEventOid
,	 	 TdProdConfigurationChangeEventValue
,	 	 tdProdConfigurationChangeEventValueValueOid
,	 	 tdSetContrParamsDirectiveOid
,	 	 TdContrParamIdsAndValues
,	 	 tdContrParamIdsAndValuesQualifierOid
,	 	 tgftHostFrOid
,	 	 mdCstsProviderFrOid
,	 	 MdSvcProdStat
,	 	 mdSvcProdStatParamOid
,	 	 MdSvcInstanceId
,	 	 mdSvcInstanceIdParamOid
,	 	 MdSvcInstanceState
,	 	 mdSvcInstanceStateParamOid
,	 	 MdInitiatorId
,	 	 mdInitiatorIdParamOid
,	 	 MdResponderId
,	 	 mdResponderIdParamOid
,	 	 MdResponderPortId
,	 	 mdResponderPortIdParamOid
,	 	 MdServiceUserRespondingTimer
,	 	 mdServiceUserRespondingTimerParamOid
,	 	 MdMinAllowedDeliveryCycle
,	 	 mdMinAllowedDeliveryCycleParamOid
,	 	 MdNamedParamLabelLists
,	 	 mdNamedParamLabelListsParamOid
,	 	 MdNamedEventLabelLists
,	 	 mdNamedEventLabelListsParamOid
,	 	 mdSvcProdStatChangeEventOid
,	 	 MdSvcProdStatChangeValue
,	 	 mdSvcProdStatChangeValueValueOid
,	 	 mdSvcProdConfgurationChangeEventOid
,	 	 MdSvcProdConfgurationChangeValue
,	 	 mdSvcProdConfgurationChangeValueValueOid
,	 	 scCstsProviderFrOid
,	 	 scProductionFrOid
;

AuthorityIdentifier 	 ::= VisibleString ((ALL EXCEPT " ")) (SIZE( 3 .. 16)) 
CfdpActionCode      	 ::= ENUMERATED
{
	 create              	 	 (0)
,	 delete              	 	 (1)
,	 rename              	 	 (2)
,	 append              	 	 (3)
,	 replace             	 	 (4)
,	 createDirectory     	 	 (5)
,	 removeDirectory     	 	 (6)
,	 denyFile            	 	 (7)
,	 denyDirectory       	 	 (8)
}

CfdpConditionCodeType	 ::= ENUMERATED
{
	 noError             	 	 (0)
,	 posAckLimitReached  	 	 (1)
,	 keepAliveAckLimitreached	 	 (2)
,	 invalidTransmissionMode	 	 (3)
,	 fileStoreRejection  	 	 (4)
,	 fileChecksumFailure 	 	 (5)
,	 fileSizeError       	 	 (6)
,	 nakLimitReached     	 	 (7)
,	 inactivityDetected  	 	 (8)
,	 invalidFileStructure	 	 (9)
,	 checkLimitReached   	 	 (10)
,	 reserved1           	 	 (11)
,	 reserved2           	 	 (12)
,	 reserved3           	 	 (13)
,	 suspendRequestReceived	 	 (14)
,	 cancelRequestReceived	 	 (15)
}

CfdpEntityId        	 ::= INTEGER  (0 .. 18446744073709551615)
CfdpFaultHandler    	 ::= ENUMERATED
{
	 cancel              	 	 (0)
,	 suspend             	 	 (1)
,	 abandon             	 	 (2)
,	 ignore              	 	 (3)
}

CfdpFaultOrAbandonedIndicationType	 ::= SEQUENCE
{
	 transactionId       	 CfdpTransactionIdType
,	 conditionCode       	 CfdpConditionCodeType
,
	 -- Progress indicates how far the issuing CFDP entity had progressed
	 progress            	 INTEGER 
}

CfdpOptionalTimer   	 ::= CHOICE
{
	 timerValue          	 [0]	 	 CfdpTimer
,	 notApplicable       	 [1]	 	 NULL
}

-- Unit is in seconds
CfdpTimer           	 ::= INTEGER  (0 .. 4294967295)
-- The Transaction ID parameter shall uniquely identify a single instance of FDU
-- delivery
--  and shall contain the ID of the source CFDP entity together with a sequence number
-- that
--  is specific to that entity.
-- NOTES
-- 1 At any moment, any given transaction ID is unique
--  within the CFDP addressing
-- domain that encompasses the source CFDP entity.
-- 2 The
--  entity ID and transaction sequence number are variable in length to
-- accommodate
--  differing mission requirements. A common parsing scheme is defined
-- to allow full
--  interoperability despite differing parameter lengths.
CfdpTransactionIdType	 ::= OCTET STRING
CfdpTransmissionModeType	 ::= ENUMERATED
{
	 acknowledged        	 	 (0)
,	 unacknowledged      	 	 (1)
}

ConvolutionalCodeRate	 ::= ENUMERATED
{
	 rate1Over2          	 	 (0)
,	 rate2Over3          	 	 (1)
,	 rate3Over4          	 	 (2)
,	 rate5Over6          	 	 (3)
,	 rate7Over8          	 	 (4)
}

ConvolutionalEncoding	 ::= CHOICE
{
	 notApplicable       	 [0]	 	 NULL
,	 applicable          	 [1]	 	 ConvolutionalCodeRate
}

-- Service Instance Identifier type for CSTSes
CstsSvcInstanceId   	 ::= SEQUENCE
{

	 -- As registered in the SANA Spacecraft Registry: https://sanaregistry.org/r/spacecraft
	 spacecraftId        	 OBJECT IDENTIFIER
,
	 -- As registered in the SANA Service Site and Aperture Registry: https://sanaregistry.org/r/service_sites_apertures
	 facilityId          	 OBJECT IDENTIFIER
,
	 -- As registered under the {...  ccsds   css   csts   services} subtree.
	 serviceType         	 OBJECT IDENTIFIER
,
	 -- The service instance number shall be identical to the Functional Resource Instance
	 --  Number of the Functional Resource Name assigned to the service instance.
	 svcInstanceNumber   	 LongIntUnsigned
}

-- Contains the data-unit-id of a data unit that has completed processing, and the service-instance-identifier
--  of the source CSTS instance
DataUnitProcessingCompletedEventValue	 ::= SEQUENCE
{
	 dataUnitId          	 LongIntPos
,	 svcInstanceId       	 CstsSvcInstanceId
}

DirectiveQualifier  	 ::= SEQUENCE
{
	 functResourceInstanceNumber	 INTEGER 
,	 directiveQualifierValues	 SEQUENCE  OF	 SEQUENCE
	 	 {
	 	 	 paramId             	 OBJECT IDENTIFIER
,	 	 	 parameterValue      	 SEQUENCE
	 	 	 {
	 	 	 	 paramTypeOid        	 OBJECT IDENTIFIER
,	 	 	 	 paramValue          	 OCTET STRING
	 	 	 }

	 	 }

}

-- Conforms to the LabelListSet type specified in the version 1 CSTS Specification Framework,
--  CCSDS 921.1-B-1
LabelListSetV1      	 ::= SET  OF	 SEQUENCE
	 {
	 	 name                	 VisibleString
,
	 	 -- Only one list in the set can be the default list.
	 	 defaultList         	 BOOLEAN
,
	 	 -- These are the version 1 labels.
	 	 labels              	 SEQUENCE  OF	 LabelV1
	 }

-- Conforms to the LabelListSet type specified in the version 2 CSTS Specification Framework,
--  CCSDS 921.1-B-2
LabelListSetV2      	 ::= SET  OF	 SEQUENCE
	 {
	 	 name                	 VisibleString
,
	 	 -- Only one list in the set can be the default list.
	 	 defaultList         	 BOOLEAN
,
	 	 -- These are the version 2 labels.
	 	 labels              	 SEQUENCE  OF	 OBJECT IDENTIFIER
	 }

LabelV1             	 ::= SEQUENCE
{
	 frOrProcedureType   	 CHOICE
	 {
	 	 functionalResourceType	 [0]	 	 OBJECT IDENTIFIER
,	 	 procedureType       	 [1]	 	 OBJECT IDENTIFIER
	 }

,	 paramOrEventId      	 OBJECT IDENTIFIER
}

LdpcCodeRate        	 ::= ENUMERATED
{
	 rate1Over2          	 	 (0)
,	 rate2Over3          	 	 (1)
,	 rate4Over5          	 	 (2)
,	 rate223Over255      	 	 (3)
}

-- The value associated with each code rate is the set of allowed information block
--  sizes that are allowed for that code rate.
LdpcCodeRateAndInfoBlockLength	 ::= CHOICE
{
	 rate1Over2          	 [0]	 	 INTEGER  (1024 | 4096 | 16384)
,	 rate2Over3          	 [1]	 	 INTEGER  (1024 | 4096 | 16384)
,	 rate4Over5          	 [2]	 	 INTEGER  (1024 | 4096 | 16384)
,
	 -- This rate is designated "rate 7/8" in CCSDS 131.0
	 rate223Over255      	 [3]	 	 INTEGER  (7136)
}

LockStat            	 ::= SEQUENCE
{
	 carrierLock         	 ENUMERATED
	 {
	 	 notLocked           	 	 (0)
	 ,	 locked              	 	 (1)
	 }

,	 subcarrierLock      	 ENUMERATED
	 {
	 	 notLocked           	 	 (0)
	 ,	 locked              	 	 (1)
	 ,	 notApplicable       	 	 (2)
	 }

,	 symbolStreamLock    	 ENUMERATED
	 {
	 	 notLocked           	 	 (0)
	 ,	 locked              	 	 (1)
	 }

}

LongIntPos          	 ::= INTEGER  (1 .. 4294967295)
LongIntUnsigned     	 ::= INTEGER  (0 .. 4294967295)
-- The engineering unit is milliseconds.
MinAllowedDeliveryCycle	 ::= INTEGER  (1 .. 3600000)
PcmFormat           	 ::= ENUMERATED
{
	 nrzL                	 	 (0)
,	 nrzM                	 	 (1)
,	 nrzS                	 	 (2)
,	 biPhaseL            	 	 (3)
,	 biPhaseM            	 	 (4)
,	 biPhaseS            	 	 (5)
}

ProdConfigurationChangeEventValue	 ::= NULL
ProdStat            	 ::= ENUMERATED
{
	 configured          	 	 (0)
,	 operational         	 	 (1)
,	 interrupted         	 	 (2)
,	 halted              	 	 (3)
}

-- This is the version 1 ProdStat type that is consistent with CSTS-SFW B-1; i.e., it
--  is expressed as a SEQUENCE OF INTEGER
ProdStatV1          	 ::= SEQUENCE  (SIZE( 1))  OF	 INTEGER 
{
	 	 	 	 configured          	 	 (0)
,	 	 	 	 operational         	 	 (1)
,	 	 	 	 interrupted         	 	 (2)
,	 	 	 	 halted              	 	 (3)
}

PublishedIdentifier 	 ::= VisibleString (FROM (ALL EXCEPT " ")) (SIZE( 3 .. 16)) 
Randomization       	 ::= ENUMERATED
{
	 off                 	 	 (0)
,	 on                  	 	 (1)
}

ResourceStat        	 ::= ENUMERATED
{
	 configured          	 	 (0)
,	 operational         	 	 (1)
,	 interrupted         	 	 (2)
,	 halted              	 	 (3)
}

ResponderPortId     	 ::= VisibleString (FROM (ALL EXCEPT " ")) (SIZE( 1 .. 128)) 
RsInterleavingDepth 	 ::= ENUMERATED
{
	 depth1              	 	 (0)
,	 depth2              	 	 (1)
,	 depth3              	 	 (2)
,	 depth4              	 	 (3)
,	 depth5              	 	 (4)
,	 depth8              	 	 (5)
}

SequenceOfGvcids    	 ::= CHOICE
{

	 -- Gvcid also requires the TFVN. for TM frames, the TFVN is '00' binary.
	 sequenceOfTmGvcids  	 [0]	 	 SEQUENCE  (SIZE( 1 .. 1024))  OF	 SEQUENCE
	 	 {
	 	 	 tmScid              	 INTEGER  (0 .. 1023)
,	 	 	 tmVcid              	 INTEGER  (0 .. 7)
	 	 }

,
	 -- The TFVN of AOS fremes is always '01' binary.
	 sequenceOfAosGvcids 	 [1]	 	 SEQUENCE  (SIZE( 1 .. 256))  OF	 SEQUENCE
	 	 {
	 	 	 aosScid             	 INTEGER  (0 .. 255)
,	 	 	 aosVcid             	 INTEGER  (0 .. 63)
	 	 }

,
	 -- The TFVN of USLP frames is always '1100' binary.
	 sequenceOfUslpGvcids	 [2]	 	 SEQUENCE  (SIZE( 1 .. 65536))  OF	 SEQUENCE
	 	 {
	 	 	 uslpScid            	 INTEGER  (0 .. 65535)
,	 	 	 uslpVcid            	 INTEGER  (0 .. 63)
	 	 }

}

ShortIntPos         	 ::= INTEGER  (1 .. 65536)
ShortIntUnsigned    	 ::= INTEGER  (0 .. 65536)
SleReportingCycle   	 ::= CHOICE
{
	 reportingOff        	 [0]	 	 NULL
,
	 -- The engineeringUnit of this parameter is second
	 reportingOn         	 [1]	 	 INTEGER  (2 .. 600)
}

SleRtnDeliveryMode  	 ::= ENUMERATED
{
	 onlineTimely        	 	 (0)
,	 onlineComplete      	 	 (1)
,	 offline             	 	 (2)
}

SleRtnProdStat      	 ::= ENUMERATED
{
	 running             	 	 (0)
,	 interrupted         	 	 (1)
,	 halted              	 	 (2)
}

-- The engineering unit of this parameter is second.
SleRtnTimeout       	 ::= INTEGER  (1 .. 600)
SleSvcInstanceId    	 ::= OCTET STRING (SIZE( 30 .. 256)) 
SleSvcInstanceState 	 ::= ENUMERATED
{
	 unbound             	 	 (0)
,	 ready               	 	 (1)
,	 active              	 	 (2)
}

-- The state of an instance of a CSTS that has a stateful prime procedure
StatefulCstsInstanceState	 ::= ENUMERATED
{
	 unbound             	 	 (0)
,	 boundReady          	 	 (1)
,	 boundActive         	 	 (2)
}

-- State of an instance of a CSTS that has a stateless prime procedure
StatelessCstsInstanceState	 ::= ENUMERATED
{
	 unbound             	 	 (0)
,	 bound               	 	 (1)
}

-- The engineering unit of this type is second
SvcUserRespTimer    	 ::= INTEGER  (1 .. 600)
TcLinkStat          	 ::= ENUMERATED
{
	 fwdLinkStatNotAvailable	 	 (0)
,	 noBitLock           	 	 (1)
,	 noRfAvailable       	 	 (2)
,	 nominal             	 	 (3)
}

TrueFalse           	 ::= ENUMERATED
{
	 true                	 	 (0)
,	 false               	 	 (1)
}

-- Specifies the Mux Control scheme type used by both the vlfUslpMcMuxContr and flfUslpMcMuxContr
--  parameters
UslpMcMuxContr      	 ::= CHOICE
{
	 fifo                	 [0]	 	 NULL
,	 absolutePriority    	 [1]	 	 SEQUENCE  (SIZE( 1 .. 65536))  OF	 INTEGER  (0 .. 65535)
,	 pollingVector       	 [2]	 	 SEQUENCE  (SIZE( 1 .. 196608))  OF	 INTEGER  (0 .. 65535)
}

-- Specifies the Mux Control scheme type used by both the vlfUslpVcMuxContr and flfUslpVcMuxContr
--  parameters
UslpVcMuxContr      	 ::= CHOICE
{
	 fifo                	 [0]	 	 NULL
,	 absolutePriority    	 [1]	 	 SEQUENCE  (SIZE( 1 .. 64))  OF	 INTEGER  (0 .. 63)
,	 pollingVector       	 [2]	 	 SEQUENCE  (SIZE( 1 .. 192))  OF	 INTEGER  (0 .. 63)
}

-- The data type of a parameter that configures and reports the USLP Master Channel
--  that is provided by the given USLP VC Multiplexing FR instance. The Master Channel
--  ID is the concatenation of TFVN and SCID. Given that this FR type handles only USLP
--  frames, the TFVN is fixed and only the SCID is variable. This type is used by both
--  the vlfUslpVcMux and flfUslpVcMux parameters.
UslpVcMuxMc         	 ::= SEQUENCE
{
	 tfvn                	 BIT STRING ('1100'B)
,	 scid                	 INTEGER  (0 .. 65535)
}

-- ITU fequency bands
FreqBands           	 ::= ENUMERATED
{
	 hf                  	 	 (0)
,	 vhf                 	 	 (1)
,	 uhf                 	 	 (2)
,	 l                   	 	 (3)
,	 s-ne                	 	 (4)
,	 s-ds                	 	 (5)
,	 c                   	 	 (6)
,	 x-ne                	 	 (7)
,	 x-ds                	 	 (8)
,	 ku                  	 	 (9)
,	 k                   	 	 (10)
,	 ka-ne               	 	 (11)
,	 ka-ds               	 	 (12)
,	 ka-s                	 	 (13)
,	 v                   	 	 (14)
,	 w                   	 	 (15)
,	 mm                  	 	 (16)
,	 o1                  	 	 (17)
,	 o2                  	 	 (18)
}

-- The Functional Resource Name.
FrName              	 ::= SEQUENCE
{

	 -- The Object Identifier for the FR type.
	 frType              	 OBJECT IDENTIFIER
,
	 -- The FR Instance Numbe of the FR instance.
	 frin                	 LongIntPos
}

-- This type contains the elements that are common to all TDM path table records.
TdmPathTableCommonElements	 ::= SEQUENCE
{

	 -- The identifier of the path record in the TDM path table
	 trackingDataPathId  	 VisibleString
,
	 -- The aperture name that populates the PARTICIPANT_1 field of the generated TDM segment.
	 apertureName        	 VisibleString
,
	 -- The space user node name that populates the PARTICIPANT_2 field of the generated
	 --  TDM segments.
	 spaceUserNodeName   	 VisibleString
,
	 -- Specifies the period (in seconds) at which the TDM segments are to be generated.
	 reportingPeriod     	 INTEGER  (1 .. 65536)
,
	 -- The FR Name of the FR that provides the tracking data measurements reported by the
	 --  TDM path.
	 frName              	 FrName
}



-- The Antenna FR accepts as input the carrier signal that shall either be radiated
--  into space or into a water load, provided the given FR instance has the transmit
--  capability. 
-- It provides as output the carrier signal received from space to the
--  Ccsds401SpaceLinkCarrierRcpt FR or the Ccsds415SpaceLinkCarrierRcpt FR and the azimuth
--  and elevation pointing angles to the TdmSegmentGen FR and NonValRmDataCollection
--  FR, provided the given FR instance has the receive capability. The pointing angles
--  are provided only while the antenna is in some form of 'closedLoop' pointing mode.
-- For
--  the correction of radiometric observables weather data are required which  should
--  be collected close to the antenna used to obtain the radiometric observables. Therefore
--  the Antenna FR is regarded as the source of the weather data provided to the TdmSegmentGeneration
--  FR and the NonValRmDataCollection FR. 
-- 
-- Note: An Antenna FR may be limited to
--  'transmit-only' or 'receive-only'.
antennaFrOid	 OBJECT IDENTIFIER ::= { 1 3 112 4 4 2 1 10100 }




-- This enumerated parameter reports the overall status of the antenna and can take
--  on four values: 
-- - 'configured': the antenna system has been configured, but is
--  not yet tracking because it is still moving to the initial pointing or the spacecraft
--  is not yet or no longer in view; 
--  - 'operational': the antenna is tracking in
--  the reported pointing mode (cf. antennaPointingMode); 
--  - 'interrupted': a failure
--  has been detected that prevents the antenna from tracking nominally; 
--  - 'halted':
--  the antenna has been taken out of service, e.g. due to wind speed requiring the
--  antenna to be put into stow position.
antResourceStatParamOid	 OBJECT IDENTIFIER ::= { 1 3 112 4 4 2 1 10100 1 1 1 1 }

AntResourceStat     	 ::= ResourceStat


-- This parameter identifies the antenna that is involved in providing a given support.
--  The antenna may either be identified by its name where typically this name is defined
--  by the operating agency so that no guarantee can be given that the identifier is
--  globally unique. Alternatively the antenna may be officially registered in SANA
--  in which case it has a globally unique Object Identifier. Knowledge of which antenna
--  is being used is needed for a number of aspects, e.g. to assess the observed signal
--  levels with respect to the antenna performance or to perform time correlation that
--  requires knowledge of the exact geographical location of the given antenna.
-- Note:
--  In case the antennas used for uplink and downlink are not identical, the Functional
--  Resource (FR) instance number shall be used to differentiate them. 
-- Antenna arrays
--  will be modeled by a dedicated FR type
antIdParamOid	 OBJECT IDENTIFIER ::= { 1 3 112 4 4 2 1 10100 1 2 1 1 }

AntId               	 ::= CHOICE
{
	 antennaName         	 [0]	 	 VisibleString (SIZE( 3 .. 16)) 
,	 antennaOid          	 [1]	 	 OBJECT IDENTIFIER
}



-- This parameter reports the current antenna azimuth pointing in 1/1000 degrees, where
--  0 degrees corresponds to pointing north and 90 degrees corresponds to pointing east.
--  Depending on the way the antenna is built, values above 360 degrees may be reported
--  in cases where the antenna enables such azimuth range as to mitigate the cable unwrap
--  issue. For antennas with a mount different from elevation over azimuth (e.g. x/y
--  mount), the antenna pointing shall be converted to the azimuth/elevation presentation.
--  This also applies to antennas having a tilt mode as to overcome the zenith track
--  singularity.
-- Note: Time-tagged antenna pointing is regarded a radiometric product
--  and therefore not part of monitoring provided by this FR type. 
antActualAzimuthParamOid	 OBJECT IDENTIFIER ::= { 1 3 112 4 4 2 1 10100 1 3 1 1 }

-- The engineering unit of this parameter is 1/1000 degree.
AntActualAzimuth    	 ::= INTEGER  (0 .. 540000)


-- This parameter reports the current antenna elevation pointing in 1/1000 degrees,
--  where 0 degrees corresponds to pointing to the horizon and 90 degrees corresponds
--  to zenith pointing. Depending on the way the antenna is built, values above 90 degrees
--  may be reported in cases where the antenna enables such elevation range as to mitigate
--  the azimuth singularity at zenith. For antennas with a mount different from elevation
--  over azimuth (e.g. x/y mount), the antenna pointing shall be converted to the azimuth/elevation
--  presentation. This also applies to antennas having a tilt mode as to overcome the
--  zenith track singularity.
-- Note: Time-tagged antenna pointing is regarded a radiometric
--  product and therefore not part of monitoring provided by this FR type. 
antActualElevationParamOid	 OBJECT IDENTIFIER ::= { 1 3 112 4 4 2 1 10100 1 4 1 1 }

-- The engineering unit of this parameter is 1/1000 degree.
AntActualElevation  	 ::= INTEGER  (0 .. 180000)


-- This parameter reports the azimuth pointing in 1/1000 degrees commanded to the servo
--  system while the antPointingMode is either 'programTrack' or 'closedLoop', where
--  0 degrees corresponds to pointing north and 90 degrees corresponds to pointing east.
--  Depending on the way the antenna is built, values above 360 degrees may be reported
--  in cases where the antenna enables such azimuth range as to mitigate the cable unwrap
--  issue. For antennas with a mount different from elevation over azimuth (e.g. x/y
--  mount), the antenna pointing shall be converted to the azimuth/elevation presentation.
--  This also applies to antennas having a tilt mode as to overcome the zenith track
--  singularity.
antCommandedAzimuthParamOid	 OBJECT IDENTIFIER ::= { 1 3 112 4 4 2 1 10100 1 5 1 1 }

-- The engineering unit of this parameter is 1/1000 degree.
AntCommandedAzimuth 	 ::= INTEGER  (0 .. 540000)


-- This parameter reports the antenna elevation pointing in 1/1000 degrees commanded
--  to the servo system while the antPointingMode is either 'programTrack' or 'closedLoop',
--  where 0 degrees corresponds to pointing to the horizon and 90 degrees corresponds
--  to zenith pointing. Depending on the way the antenna is built, values above 90 degrees
--  may be reported in cases where the antenna enables such elevation range as to mitigate
--  the azimuth singularity at zenith. For antennas with a mount different from elevation
--  over azimuth (e.g. x/y mount), the antenna pointing shall be converted to the azimuth/elevation
--  presentation. This also applies to antennas having a tilt mode as to overcome the
--  zenith track singularity.
antCommandedElevationParamOid	 OBJECT IDENTIFIER ::= { 1 3 112 4 4 2 1 10100 1 6 1 1 }

-- The engineering unit of the parameter is 1/1000 degree.
AntCommandedElevation	 ::= INTEGER  (0 .. 180000)


-- This parameter configures and reports the azimuth in 1/1000 degrees the antenna shall
--  point to when the pointing-mode is set to 'fixedPosition',  where 0 degrees corresponds
--  to pointing north and 90 degrees corresponds to pointing east. Depending on the
--  way the antenna is built, values above 360 degrees may be supported in cases where
--  the antenna enables such azimuth range as to mitigate the cable unwrap issue. For
--  antennas with a mount different from elevation over azimuth (e.g. x/y mount), the
--  antenna pointing shall be converted to the azimuth/elevation presentation. This
--  also applies to antennas having a tilt mode as to overcome the zenith track singularity.
antContrAzimuthParamOid	 OBJECT IDENTIFIER ::= { 1 3 112 4 4 2 1 10100 1 7 1 1 }

-- The engineering unit of this parameter is 1/1000 degree.
AntContrAzimuth     	 ::= INTEGER  (0 .. 540000)


-- This parameter configures and reports the elevation in 1/1000 degrees the antenna
--  shall point to when the pointing-mode is set to 'fixedPosition',  where 0 degrees
--  corresponds to pointing to the local horizon and 90 degrees corresponds to zenith
--  pointing. Depending on the way the antenna is built, values above 90 degrees may
--  be reported in cases where the antenna enables such elevation range as to mitigate
--  the azimuth singularity at zenith. For antennas with a mount different from elevation
--  over azimuth (e.g. x/y mount), the antenna pointing shall be converted to the azimuth/elevation
--  presentation. This also applies to antennas having a tilt mode as to overcome the
--  zenith track singularity. 
antContrElevationParamOid	 OBJECT IDENTIFIER ::= { 1 3 112 4 4 2 1 10100 1 8 1 1 }

-- The engineering unit of this parameter is 1/1000 degree.
AntContrElevation   	 ::= INTEGER  (0 .. 180000)


-- The parameter configures and reports the azimuth angular rate in 1/1000 degrees per
--  second at which the antenna shall move when  antPointingMode is set to 'slew'. 
antContrAzimuthRateParamOid	 OBJECT IDENTIFIER ::= { 1 3 112 4 4 2 1 10100 1 9 1 1 }

-- The engineering unit of this parameter is 1/1000 degree per second.
AntContrAzimuthRate 	 ::= INTEGER  (-5000 .. 5000)


-- The parameter configures and reports the elevation angular rate in 1/1000 degrees
--  per second at which the antenna shall move when the antPointingMode is set to 'slew'.
--  
antContrElevationRateParamOid	 OBJECT IDENTIFIER ::= { 1 3 112 4 4 2 1 10100 1 10 1 1 }

-- The engineering unit of this parameter is 1/000 degree per second.
AntContrElevationRate	 ::= INTEGER  (-5000 .. 5000)


-- This parameter reports the azimuth residual (actual azimuth in closed-loop tracking
--  minus the azimuth calculated for antPointingMode = 'programTrack') in 1/1000 degrees.
--  Consequently this parameter will only be valid if antPointingMode = 'closedLoop'.
--  Antennas not having or not being operated in any closed-loop tracking mode cannot
--  provide this parameter and in this case the parameter shall be flagged as unavailable.
--  
-- Note: Time-tagged antenna pointing is regarded a radiometric product and therefore
--  not part of monitoring.  
antAzimuthResidualParamOid	 OBJECT IDENTIFIER ::= { 1 3 112 4 4 2 1 10100 1 11 1 1 }

-- The engineering unit of this parameter is 1/1000 degree.
AntAzimuthResidual  	 ::= INTEGER  (-540000 .. 540000)


-- This parameter reports the elevation residual (actual elevation in closed-loop tracking
--  minus the elevation calculated for antPointingMode = 'programTrack') in 1/1000 degrees.
--  Consequently this parameter will only be valid if antPointingMode = 'closedLoop'.
--  Antennas not having or not being operated in any closed-loop tracking mode cannot
--  provide this parameter and in this case the parameter shall be flagged as unavailable.
--  
-- Note: Time-tagged antenna pointing is regarded a radiometric product and therefore
--  not part of monitoring.  
antElevationResidualParamOid	 OBJECT IDENTIFIER ::= { 1 3 112 4 4 2 1 10100 1 12 1 1 }

-- The engineering unit of this parameter is 1/1000 degree.
AntElevationResidual	 ::= INTEGER  (-180000 .. 180000)


-- This parameter reports the azimuth aberration relative to the forward beam and the
--  return beam in 1/1000 degree. In case the provider applies aberration correction,
--  the effect of this correction shall be factured into the aberration values reported.
--  
-- A valid parameter can only be reported if antPointingMode is 'closedLoop' or 'programTrack'.
-- 
antAzimuthAberrationParamOid	 OBJECT IDENTIFIER ::= { 1 3 112 4 4 2 1 10100 1 13 1 1 }

AntAzimuthAberration	 ::= SEQUENCE
{

	 -- The engineering unit of this element is 1/1000 degree.
	 fwdBeamAberration   	 INTEGER  (-1000 .. 1000)
,
	 -- The engineering unit of this element is 1/1000 degree.
	 rtnBeamAberration   	 INTEGER  (-1000 .. 1000)
}



-- This parameter reports the elevation aberration relative to the forward beam and
--  the return beam in 1/1000 degree. In case the provider applies aberration correction,
--  the effect of this correction shall be factured into the aberration values reported.
--  
-- A valid parameter can only be reported if antPointingMode is 'closedLoop' or 'programTrack'.
-- 
antElevationAberrationParamOid	 OBJECT IDENTIFIER ::= { 1 3 112 4 4 2 1 10100 1 14 1 1 }

AntElevationAberration	 ::= SEQUENCE
{

	 -- The engineering unit of this element is 1/1000 degree.
	 fwdBeamAberration   	 INTEGER  (-1000 .. 1000)
,
	 -- The engineering unit of this element is 1/1000 degree.
	 rtnBeamAberration   	 INTEGER  (-1000 .. 1000)
}



-- This enumerated parameter configures and reports the pointing mode of the antenna
--  servo system. The values this parameter can take on are:
-- - 'stow': the antenna
--  is in or is moving to its stow position;
-- - 'halt': the antenna has been stopped
--  in its current position;
-- - 'fixedPosition': the antenna is moving to or has moved
--  to the specified azimuth and elevation;
-- - 'slew': the antenna is moving at commanded
--  angular rates;
-- - 'programTrack': the antenna is pointed in accordance with spacecraft
--  trajectory predicts;
-- - 'closedLoop': the antenna is pointing in closed-loop mode.
-- Antenna
--  implementations will typically support only a subset of the above listed pointing
--  modes.
antPointingModeParamOid	 OBJECT IDENTIFIER ::= { 1 3 112 4 4 2 1 10100 1 15 1 1 }

AntPointingMode     	 ::= ENUMERATED
{
	 stow                	 	 (0)
,	 halt                	 	 (1)
,	 fixedPosition       	 	 (2)
,	 slew                	 	 (3)
,	 programTrack        	 	 (4)
,	 closedLoop          	 	 (5)
}



-- This parameter configures and reports the settings applied to 'closedLoop' antenna
--  pointing mode, either to monopulse tracking or to conical scann tracking. 
antClosedLoopConfigurationParamOid	 OBJECT IDENTIFIER ::= { 1 3 112 4 4 2 1 10100 1 16 1 1 }

AntClosedLoopConfiguration	 ::= CHOICE
{

	 -- For monopulse tracking no required configuration parameters have been identified.
	 monopulse           	 [0]	 	 NULL
,
	 -- The engineering unit of this element is 1/1000 degrees
	 conicalScan         	 [1]	 	 INTEGER  (1 .. 5000)
}



-- This parameter reports the mode in which the return signal is tracked for antenna
--  steering provided the antPointingMode = 'closedLoop'. The mode is chosen depending
--  on the modulation scheme. 
-- The values the parameter may have are:
-- - 'carrierTrackingMode':
--  the receiver tracks the remnant carrier by means of a carrier tracking PLL when
--  ccsds401CarrierRcptModulationType is either 'subcarrier' or 'direct';
-- - 'crossCorrelationMode':
--  the receiver tracks the return link signal by means of checking for the spectral
--  symmetry when ccsds401CarrierRcptModulationType is neither 'subcarrier' nor 'direct'.
-- 
antTrackingRxModeParamOid	 OBJECT IDENTIFIER ::= { 1 3 112 4 4 2 1 10100 1 17 1 1 }

AntTrackingRxMode   	 ::= ENUMERATED
{
	 carrierTrackingMode 	 	 (0)
,	 crossCorrelationMode	 	 (1)
}



-- This enumerated parameter configures and reports the polarization of the channel
--  that shall be used for tracking purposes. If 'autoHysteresis' is chosen, the parameter
--  specifies how much larger in 1/10 dB the power observed for the unselected polarization
--  must be before a switch-over to the polarization with the stronger signal is performed.
-- 
-- If
--  the same receiver is used for telemetry reception and antenna steering, setting
--  of this parameter is not possible and the value reported by this is a copy of the
--  ccsds401CarrierRcptPolarization parameter or a TBD parameter of the CCSDS 415 Return
--  Channel Reception FR Set.
antTrackingSignalPolarizationParamOid	 OBJECT IDENTIFIER ::= { 1 3 112 4 4 2 1 10100 1 18 1 1 }

AntTrackingSignalPolarization	 ::= CHOICE
{
	 lhc                 	 [0]	 	 NULL
,	 rhc                 	 [1]	 	 NULL
,
	 -- The engineering unit of this element is 1/10 dB.
	 autoHysteresis      	 [2]	 	 INTEGER  (0 .. 100)
,
	 -- The engineering unit of this element is Hertz.
	 combining           	 [3]	 	 INTEGER  (10 .. 100000)
}



-- This parameter reports the return link signal level in tenth of dBm as observed by
--  the tracking receiver, i.e., the signal level derived from the tracking receiver
--  AGC reading. As to have comparable, i.e., station level plan independent values,
--  the level reading should be calibrated to the LNA input. Due to the levels to be
--  expected, the numbers will always be negative.
-- 
-- If the same receiver is used for
--  telemetry reception and antenna steering, the value reported by this is a copy of
--  the ccsds401CarrierRcptSignalLevel parameter or a TBD parameter of the CCSDS 415
--  Return Channel Reception FR Set. 
-- If a tracking receiver is not available or not
--  used, this parameter shall be flagged as undefined.
-- In some implementations one
--  receiver may be used both for antenna tracking and reception of telemetry and ranging.
--  If so, the parameters of that receiver will be represented in both the Antenna FR
--  type and the Rtn401SpaceLinkCarrierRcpt FR type.
antTrackingRxInpLevelParamOid	 OBJECT IDENTIFIER ::= { 1 3 112 4 4 2 1 10100 1 19 1 1 }

-- The engineering unit of this 1/10 dBm
AntTrackingRxInpLevel	 ::= INTEGER  (-2000 .. -30)


-- This parameter configures and reports the nominal return carrier frequency disregarding
--  any Doppler shift. 
-- 
-- If the same receiver is used for telemetry reception and
--  antenna steering, setting of this parameter is not possible and the value reported
--  by this is a copy of the ccsds401CarrierRcptNominalFreq parameter or a TBD parameter
--  of the CCSDS 415 Return Channel Reception FR Set.  
-- 
antTrackingRxNominalFreqParamOid	 OBJECT IDENTIFIER ::= { 1 3 112 4 4 2 1 10100 1 20 1 1 }

-- The engineering unit of this parameter is Hertz.
AntTrackingRxNominalFreq	 ::= INTEGER  (2200000000 .. 32300000000)


-- This parameter configures and reports the band in Hz centered around the antTrackingRxNominalFreq,
--  possibly corrected for the expected Doppler offset (as configured by the antTrackingRxPredictMode
--  parameter) in which the receiver shall search for the carrier signal. This parameter
--  is also valid in case of a suppressed carrier modulation scheme.
-- 
-- If the same
--  receiver is used for telemetry reception and antenna steering, setting of this parameter
--  is not possible and the value reported by this is a copy of the ccsds401CarrierRcptFreqSearchRange
--  parameter or a TBD parameter of the CCSDS 415 Return Channel Reception FR Set. 
--  
antTrackingRxFreqSearchRangeParamOid	 OBJECT IDENTIFIER ::= { 1 3 112 4 4 2 1 10100 1 21 1 1 }

-- The engineering unit of this parameter is Hertz.
AntTrackingRxFreqSearchRange	 ::= INTEGER  (0 .. 1500000)


-- This enumerated parameter configures and reports for which condition the Doppler
--  predicts have been calculated. It can take on four values:
-- - none: no information
--  regarding the expected Doppler shift is available and therefore the nominal frequency
--  is used;
-- - oneWay: this mode will be used when the spacecraft is not locked to
--  a forward link signal or while the spacecraft transponder is commanded to non-coherent
--  mode or when the spacecraft receiver is in 'coherency enabled' mode and the forward
--  link carrier frequency is ramped such that the Doppler on the forward link is compensated,
--  i.e., the spacecraft always 'sees' the nominal forward link frequency; in this case
--  it does not matter if the forward link is radiated by the same station as the one
--  that is receiving the return link or a different station; 
-- - twoWay: this mode
--  is applied when the spacecraft receiver is commanded to 'coherency enabled' mode
--  and the station that is receiving the return link also radiates the forward link,
--  the latter at a constant frequency;
-- - threeWay: this mode is applied when the spacecraft
--  receiver is in 'coherency enabled' mode and a station different from the one receiving
--  the return link is radiating the forward link signal at a known constant frequency.
-- 
-- If
--  the same receiver is used for telemetry reception and antenna steering, setting
--  of this parameter is not possible and the value reported by this is a copy of the
--  ccsds401CarrierRcptPredictMode parameter or a TBD parameter of the CCSDS 415 Return
--  Channel Reception FR Set.  
-- 
antTrackingRxPredictModeParamOid	 OBJECT IDENTIFIER ::= { 1 3 112 4 4 2 1 10100 1 22 1 1 }

AntTrackingRxPredictMode	 ::= ENUMERATED
{
	 none                	 	 (0)
,	 oneWay              	 	 (1)
,	 twoWay              	 	 (2)
,	 threeWay            	 	 (3)
}



-- This parameter configures and reports the dual-sided tracking loop bandwidth in tenth
--  Hz of the receiver. Depending on the mode the tracking receiver operates in, this
--  is either the bandwidth of the PLL tracking the remnant carrier or the frequency
--  range observed for checking spectral symmetry. 
-- 
-- This parameter also configures
--  and reports the duration in seconds within which the bandwidth reduction to the
--  newly commanded loop bandwidth shall be reached. This gradual change of the loop
--  bandwidth is intended to avoid loss of lock. The duration for the gradual bandwidth
--  change can be set to 'auto' or set to a specific duration. If the duration is set
--  to 0, the newly commanded bandwidth is applied immediately. 
-- 
-- If the same receiver
--  is used for telemetry reception and antenna steering, setting of this parameter
--  is not possible and the value reported by this is a copy of the ccsds401CarrierRcptTrackingLoopBwdth
--  parameter or a TBD parameter of the CCSDS 415 Return Channel Reception FR Set. 
antTrackingRxLoopBwdthParamOid	 OBJECT IDENTIFIER ::= { 1 3 112 4 4 2 1 10100 1 23 1 1 }

AntTrackingRxLoopBwdth	 ::= SEQUENCE
{

	 -- The engineering unit of this element is 1/10 Hertz
	 trackingLoopBwdth   	 INTEGER  (1 .. 50000000)
,	 loopBwdthChangeDuration	 CHOICE
	 {

	 	 -- The time during which the bandwidth is gradually changed to the newly set value is
	 	 --  chosen automatically.
	 	 auto                	 [0]	 	 NULL
,
	 	 -- The engineering unit of this element is second.
	 	 bwdthChangeDuration 	 [1]	 	 INTEGER  (0 .. 100)
	 }

}



-- This enumerated parameter configures and reports the order of the carrier tracking
--  loop. It can take on the following values:
-- - 'first order': such loop is hardly
--  ever used because it has a static phase error even in case of a constant return
--  link carrier frequency;
-- - 'second order': this is the most commonly used loop as
--  it has no static phase error for a constant return link carrier frequency;
-- - 'third
--  order': such configuration may have to be used in case of high Doppler rates, as
--  such loop has no static phase error even when the return link carrier frequency
--  is sweeping, but initial acquisition is more difficult with such loop. 
-- 
-- If the
--  same receiver is used for telemetry reception and antenna steering, setting of this
--  parameter is not possible and the value reported by this is a copy of the ccsds401CarrierRcptOrderOfLoop
--  parameter or a TBD parameter of the CCSDS 415 Return Channel Reception FR Set. 
antTrackingRxOrderOfLoopParamOid	 OBJECT IDENTIFIER ::= { 1 3 112 4 4 2 1 10100 1 24 1 1 }

AntTrackingRxOrderOfLoop	 ::= ENUMERATED
{
	 firstOrder          	 	 (0)
,	 secondOrder         	 	 (1)
,	 thirdOrder          	 	 (2)
}



-- This enumerated parameter reports the lock status of the receiver and as such is
--  only supported by antennas that are configured to operate in antPointingMode = 'closedLoop'
--  mode. The values the parameter may have are:
-- - 'notLocked': the tracking receiver
--  is not locked on the return link signal and therefore cannot drive the antenna pointing;
--  
-- - 'locked': the tracking receiver has locked on the return link signal and consequently
--  is driving the antenna pointing.
-- As a consequence, the antPointingMode will have
--  changed to 'programTrack' and won't return to 'closedLoop' until receiver lock is
--  (re-)acquired. 
-- 
-- If the same receiver is used for telemetry reception and antenna
--  steering, the value reported by this is a copy of the element carrierLock of the
--   ccsds401CarrierRcptCarrierLockStat parameter or a TBD parameter of the CCSDS 415
--  Return Channel Reception FR Set. 
antTrackingRxLockStatParamOid	 OBJECT IDENTIFIER ::= { 1 3 112 4 4 2 1 10100 1 25 1 1 }

AntTrackingRxLockStat	 ::= ENUMERATED
{
	 notLocked           	 	 (0)
,	 locked              	 	 (1)
}



-- This parameter configures and reports the length in minutes of the period during
--  which the wind speed and peak wind speed are observed for the calculation of the
--  antMeanWindSpeed and antPeakWindSpeed parameters.
antWindIntegrationTimeParamOid	 OBJECT IDENTIFIER ::= { 1 3 112 4 4 2 1 10100 1 26 1 1 }

-- The engineering unit of this parameter is minutes.
AntWindIntegrationTime	 ::= INTEGER  (1 .. 60)


-- This parameter reports the wind speed as observed close to the antenna. This parameter
--  is measured in tenth m/s and averaged over the most recent period where the length
--  of the period is specified by the antWindIntegrationTime parameter.
antMeanWindSpeedParamOid	 OBJECT IDENTIFIER ::= { 1 3 112 4 4 2 1 10100 1 27 1 1 }

-- The engineering unit of this parameter is 1/10 meter per second.
AntMeanWindSpeed    	 ::= INTEGER  (0 .. 1000)


-- This parameter reports the highest wind speed observed close to the antenna during
--  the most recent period where the length of the period is specified by the antWindIntegrationTime
--  parameter. This parameter is measured in tenth m/s.
antPeakWindSpeedParamOid	 OBJECT IDENTIFIER ::= { 1 3 112 4 4 2 1 10100 1 28 1 1 }

-- The engineering unit of this parameter is 1/10 meter per second.
AntPeakWindSpeed    	 ::= INTEGER  (0 .. 1000)


-- This parameter reports the current wind direction in degrees, where 0 degrees corresponds
--  to north and 90 degrees to east.
antWindDirectionParamOid	 OBJECT IDENTIFIER ::= { 1 3 112 4 4 2 1 10100 1 29 1 1 }

-- The engineering unit of this parameter is degree.
AntWindDirection    	 ::= INTEGER  (0 .. 359)


-- This parameter reports the amount of precipitation in mm that accumulated since 0:00
--  UTC of the current day.
antAccumulatedPrecipitationParamOid	 OBJECT IDENTIFIER ::= { 1 3 112 4 4 2 1 10100 1 30 1 1 }

-- The engineering unit of this parameter is millimeter.
AntAccumulatedPrecipitation	 ::= INTEGER  (0 .. 100)


-- This parameter reports the precipitation rate in mm/h as observed during the most
--  recent hour.
antPrecipitationRateParamOid	 OBJECT IDENTIFIER ::= { 1 3 112 4 4 2 1 10100 1 31 1 1 }

-- The engineering unit of this parameter is millimeter per hour.
AntPrecipitationRate	 ::= INTEGER  (0 .. 100)


-- This parameter reports the relative humidity in % as observed by an outdoor meteorological
--  sensor close to the antenna. This parameter shall be flagged as invalid if the value
--  from the meteo unit is invalid and it shall be flagged as unavailable if this parameter
--  is not available at this time.
-- Note: Time-tagged meteo data (relative humidity,
--  atmospheric pressure, temperature) is regarded a radiometric product and therefore
--  not part of the monitoring data.
antRelativeHumidityParamOid	 OBJECT IDENTIFIER ::= { 1 3 112 4 4 2 1 10100 1 32 1 1 }

-- The engineering unit of this parameter is percent.
AntRelativeHumidity 	 ::= INTEGER  (0 .. 100)


-- This parameter reports the atmospheric pressure in hPa as observed by an outdoor
--  meteorological sensor at the station. This parameter shall be flagged as invalid
--  if the value from the meteo unit is invalid and it shall be flagged as unavailable
--  if this parameter is not available at this time.
antAtmosphericPressureParamOid	 OBJECT IDENTIFIER ::= { 1 3 112 4 4 2 1 10100 1 33 1 1 }

-- The engineering unit of this parameter is 100 Pascal (hPa).
AntAtmosphericPressure	 ::= INTEGER  (800 .. 1100)


-- This parameter reports the temperature in °C as observed by an outdoor meteorological
--  sensor at the station. This parameter shall be flagged as invalid if the value from
--  the meteo unit is invalid and it shall be flagged as unavailable if this parameter
--  is not available at this instant in time.
antAmbientTemperatureParamOid	 OBJECT IDENTIFIER ::= { 1 3 112 4 4 2 1 10100 1 34 1 1 }

-- The engineering unit of this parameter is degree Celsius.
AntAmbientTemperature	 ::= INTEGER  (-100 .. 100)


-- This event notifies any change of the antResourceStat parameter.
antResourceStatChangeEventOid	 OBJECT IDENTIFIER ::= { 1 3 112 4 4 2 1 10100 2 1 1 }




-- The event value reports the antResourceStatValue that applies since the notified
--  antResourceStatChange event occurred.
antResourceStatChangeEventValueValueOid	 OBJECT IDENTIFIER ::= { 1 3 112 4 4 2 1 10100 2 1 1 1 }

AntResourceStatChangeEventValue	 ::= AntResourceStat


-- This event notifies any change of the antTrackingRxLockStat parameter.
antTrackingRxLockStatChangeEventOid	 OBJECT IDENTIFIER ::= { 1 3 112 4 4 2 1 10100 2 2 1 }




-- The event value reports the antTrackingRxLockStat that applies since the notified
--  antTrackingRxLockStatChange event occurred.
antTrackingRxLockStatChangeEventValueValueOid	 OBJECT IDENTIFIER ::= { 1 3 112 4 4 2 1 10100 2 2 1 1 }

AntTrackingRxLockStatChangeEventValue	 ::= AntTrackingRxLockStat


-- This event notifies that gusts exceed the nominal wind speed the antenna can withstand
--  in operation and therefore the antenna may have to or will be moved to its stow
--  position.
antWindSpeedWarningEventOid	 OBJECT IDENTIFIER ::= { 1 3 112 4 4 2 1 10100 2 3 1 }




-- The event value reports if the wind condition are critical in the sense that stowing
--  of the antenna might become necessary ('warning') or that the wind speed necessitates
--  the immediate stowing of the antenna ('stowing').
antWindSpeedWarningEventValueValueOid	 OBJECT IDENTIFIER ::= { 1 3 112 4 4 2 1 10100 2 3 1 1 }

AntWindSpeedWarningEventValue	 ::= ENUMERATED
{
	 stowing             	 	 (0)
,	 warning             	 	 (1)
}



-- This directive permits setting of the controllable parameters of the Antenna FR type.
--  
antSetContrParamsDirectiveOid	 OBJECT IDENTIFIER ::= { 1 3 112 4 4 2 1 10100 3 1 1 }




-- The directive qualifier specifies the FR instance the directive shall act on and
--  contains a set of parameter identifier and parameter value pairs. To be valid, the
--  parameter identifier must reference a controllable parameter of the antenna FR and
--  the parameter value must be of the same type as the parameter value that shall be
--  set.
antContrParamIdsAndValuesQualifierOid	 OBJECT IDENTIFIER ::= { 1 3 112 4 4 2 1 10100 3 1 1 1 }

AntContrParamIdsAndValues	 ::= DirectiveQualifier


-- This FR type is TBD
antArrayFrOid	 OBJECT IDENTIFIER ::= { 1 3 112 4 4 2 1 10101 }




-- The Ccsds401SpaceLinkCarrierXmit FR accepts as input for modulation of the carrier
--  the optionally convolutionally encoded physical channel symbol stream from the FlfFrameSyncChnEncodeAndOidGen
--  FR or from the TcPlopSyncAndChnlEncode FR. It also accepts from the RngXmit FR the
--  ranging signal for modulation of the carrier.
-- The Ccsds401SpaceLinkCarrierXmit
--  FR provides the to be radiated carrier signal to the antenna FR and the actual carrier
--  frequency and phase to the NonValRmDataCollection FR. 	
ccsds401SpaceLinkCarrierXmitFrOid	 OBJECT IDENTIFIER ::= { 1 3 112 4 4 2 1 20100 }




-- This enumerated parameter reports the ccsds401SpaceLinkCarrierXmit FR resource status
--  and can take on four values:
-- - 'configured': the transmit equipment has been configured,
--  but the carrier has not been brought up or has been stopped;
-- - 'operational': the
--  transmit link is active, i.e., the carrier is up;
-- - 'interrupted': a failure has
--  been detected, e.g. carrier still on outside the transmission mask, that resulted
--  in the carrier being shut down;
-- - 'halted': the transmit link has been taken out
--  of service, e.g. due to failed HPA cooling.
ccsds401CarrierXmitResourceStatParamOid	 OBJECT IDENTIFIER ::= { 1 3 112 4 4 2 1 20100 1 1 1 1 }

Ccsds401CarrierXmitResourceStat	 ::= ResourceStat


-- This parameter configures and reports the name assigned to the physical transmission
--  channel. This name is a Visible String which has a length of 1 to 32 characters.
ccsds401CarrierXmitPhysChnlNameParamOid	 OBJECT IDENTIFIER ::= { 1 3 112 4 4 2 1 20100 1 2 1 1 }

Ccsds401CarrierXmitPhysChnlName	 ::= VisibleString (SIZE( 1 .. 32)) 


-- This enumerated parameter configures and reports the current state of the carrier
--  radiation and can take on three values:
-- - 'radiating into space': the carrier is
--  presently up and the signal is radiated via the antenna;
-- - 'radiating into test
--  load': the carrier is presently up and the signal is radiated into the water load;
-- -
--  'non-radiating': the carrier is presently down, i.e., no signal is being radiated.
ccsds401CarrierXmitStatParamOid	 OBJECT IDENTIFIER ::= { 1 3 112 4 4 2 1 20100 1 3 1 1 }

Ccsds401CarrierXmitStat	 ::= ENUMERATED
{
	 nonRadiating        	 	 (0)
,	 radiatingIntoSpace  	 	 (1)
,	 radiatingIntoTestLoad	 	 (2)
}



-- This parameter configures and reports the current transmit link signal level expressed
--  as Equivalent Isotropically Radiated Power (EIRP) in dBW.
ccsds401CarrierXmitEirpParamOid	 OBJECT IDENTIFIER ::= { 1 3 112 4 4 2 1 20100 1 4 1 1 }

-- The engineering unit of this parameter is dBW.
Ccsds401CarrierXmitEirp	 ::= INTEGER  (0 .. 150)


-- This enumerated parameter configures and reports the configured transmit link polarization
--  and can take on two values:
-- - 'lcp': the carrier is radiated with left hand circular
--  polarization;
-- - 'rcp': the carrier is radiated in right hand circular polarization.
-- Note:
--  Polarization is defined from the point of view of the source, i.e., in the direction
--  of the wave propagation.
ccsds401CarrierXmitPolarizationParamOid	 OBJECT IDENTIFIER ::= { 1 3 112 4 4 2 1 20100 1 5 1 1 }

Ccsds401CarrierXmitPolarization	 ::= ENUMERATED
{
	 lhc                 	 	 (0)
,	 rhc                 	 	 (1)
}



-- This parameter reports the current transmit frequency in Hz. In general, the frequency
--  will be constant, except during the transmit link sweep and for Category B missions
--  in case the transmit link is being ramped to compensate the Doppler shift and rate
--  on the transmit link.
ccsds401CarrierXmitActualCarrierFreqParamOid	 OBJECT IDENTIFIER ::= { 1 3 112 4 4 2 1 20100 1 6 1 1 }

-- The engineering unit of this parameter is Hertz.
Ccsds401CarrierXmitActualCarrierFreq	 ::= INTEGER  (2015000000 .. 40500000000)


-- This parameter configures and reports the nominal transmit link frequency in Hz and
--  if the transmit link frequency shall be ramped to compensate the 1-way Doppler offset.
ccsds401CarrierXmitNominalCarrierFreqParamOid	 OBJECT IDENTIFIER ::= { 1 3 112 4 4 2 1 20100 1 7 1 1 }

-- The engineering unit of this parameter is Hertz / none.
Ccsds401CarrierXmitNominalCarrierFreq	 ::= SEQUENCE
{

	 -- The engineering unit of this element is Hertz.
	 nominalXmitFreq     	 INTEGER  (2025000000 .. 40500000000)
,	 xmitLinkRamping     	 ENUMERATED
	 {
	 	 rampingOff          	 	 (0)
	 ,	 rampingOn           	 	 (1)
	 }

}



-- This enumerated parameter reports if the frequency generation of the FR is locked
--  to a reference frequency or free running. It can take on the values
-- - 'lockedToRefFreq;
-- -
--  'noRefFreqAvailable'.
ccsds401CarrierXmitReferenceFreqLockParamOid	 OBJECT IDENTIFIER ::= { 1 3 112 4 4 2 1 20100 1 8 1 1 }

Ccsds401CarrierXmitReferenceFreqLock	 ::= ENUMERATED
{
	 noRefFreqAvailable  	 	 (0)
,	 lockedToRefFreq     	 	 (1)
}



-- This enumerated parameter configures and reports the current state of the carrier
--  sweep and can take on two values:
-- - 'active': the carrier is presently being swept;
-- -
--  'not active': the carrier is presently not being swept, i.e., the nominal frequency
--  possibly compensated for Doppler is being radiated. 
-- Modulation shall be forced
--  off, whenever the sweep is active. In case the transmit link frequency is being
--  ramped to compensater Doppler shift and rate on the transmit link (Category B missions
--  only), this is not regarded to be a sweep.
-- The sweep procedure is started by setting
--  the ccsds401CarrierXmitSweepProcStat parameter to 'active' by means of the ccsds401CarrierXmitSetContrParams
--  directive. Once the sweep procedure as specified by the parameter ccsds401CarrierXmitSweepProfile
--  is completed, the ccsds401CarrierXmitSweepProcStat parameter is set automatically
--  to 'notActive'. and modulation by TC and ranging is (re-)enabled. 
-- If necessary,
--  the sweep procedure while executing can be stopped by setting the ccsds401CarrierXmitSweepProcStat
--  parameter to 'notActive' using the ccsds401CarrierXmitSetContrParams directive.
--  In that case the transmit link carrier frequency jumps back to the frequency set
--  by the ccsds401CarrierXmitNominalCarrierFreq parameter, compensated for 1-way Doppler
--  if so configured.
ccsds401CarrierXmitSweepProcStatParamOid	 OBJECT IDENTIFIER ::= { 1 3 112 4 4 2 1 20100 1 9 1 1 }

Ccsds401CarrierXmitSweepProcStat	 ::= ENUMERATED
{
	 active              	 	 (0)
,	 notActive           	 	 (1)
}



-- This complex parameter configures and reports the start frequency in Hz of the first
--  leg of the sweep and for each leg it then specifies the stop frequency in Hz, the
--  sweep rate in Hz/s and the duration of the dwell period in seconds (i.e., the time
--  during which the carrier frequency is not changed) before the next leg is started.
--  The assumption is that there are no frequency discontinuities, i.e., the start frequency
--  of a sweep leg is always equal to the stop frequency of the previous leg.
-- 
-- If
--  parameter ccsds401CarrierXmitNominalCarrierFreq is configured such that by means
--  of ramping of the transmit link frequency the 1-way Doppler is compensated, then
--  the specified sweep profile frequencies will be modified automatically in accordance
--  with the Doppler offset applicable at the given time.
ccsds401CarrierXmitSweepProfileParamOid	 OBJECT IDENTIFIER ::= { 1 3 112 4 4 2 1 20100 1 10 1 1 }

Ccsds401CarrierXmitSweepProfile	 ::= SEQUENCE
{

	 -- The engineering unit of this parameter is Hertz.
	 startfreq           	 INTEGER  (2025000000 .. 40500000000)
,	 sweepLegs           	 SEQUENCE  (SIZE( 1 .. 5))  OF	 SEQUENCE
	 	 {

	 	 	 -- The engineering unit of this parameter is second
	 	 	 dwellTime           	 INTEGER  (0 .. 20)
,
	 	 	 -- The engineering unit of this parameter is Hertz per second.
	 	 	 sweepRate           	 INTEGER  (1 .. 32000)
,
	 	 	 -- The engineering unit of this parameter is Hertz.
	 	 	 endFreq             	 INTEGER  (2025000000 .. 40500000000)
	 	 }

}



-- This enumerated parameter configures and reports the current state of the carrier
--  modulation and can take on two values:
-- - 'on': the carrier is presently being modulated;
-- -
--  'off': the carrier is presently not being modulated.
-- Note: This parameter reports
--  the modulation being off also when this is not explicitly commanded, e.g. when it
--  is forced to 'off' automatically because the transmit link sweep is active (ccsds401CarrierXmitSweepProcedure
--  = 'active').
ccsds401CarrierXmitModParamOid	 OBJECT IDENTIFIER ::= { 1 3 112 4 4 2 1 20100 1 11 1 1 }

Ccsds401CarrierXmitMod	 ::= ENUMERATED
{
	 off                 	 	 (0)
,	 on                  	 	 (1)
}



-- This parameter reports on the status of the two modulator inputs for TC and Rng.
--  Both will be disabled when ccsds401CarrierXmitMod = 'off' or ccsds401CarrierXmitSweepProcStat
--  = 'active'. The TC input will be enabled when ccsds401CarrierXmitMod = 'on' and
--  ccsds401CarrierXmitSweepProcStat = 'notActive'. The Rng input will be enabled under
--  the same conditions except if the TC input is being used and ccsds401CarrierXmitTcPriority
--  = 'yes'. 
ccsds401CarrierXmitModInpStatParamOid	 OBJECT IDENTIFIER ::= { 1 3 112 4 4 2 1 20100 1 12 1 1 }

Ccsds401CarrierXmitModInpStat	 ::= SEQUENCE
{
	 tcInp               	 ENUMERATED
	 {
	 	 disabled            	 	 (0)
	 ,	 enabled             	 	 (1)
	 }

,	 rngInp              	 ENUMERATED
	 {
	 	 disabled            	 	 (0)
	 ,	 enabled             	 	 (1)
	 }

}



-- This enumerated parameter configures and reports if the ranging signal shall be suppressed
--  in the presence of a to be radiated telecommand signal. It can take on the values
-- 'yes'
-- 'no'
ccsds401CarrierXmitTcPriorityParamOid	 OBJECT IDENTIFIER ::= { 1 3 112 4 4 2 1 20100 1 13 1 1 }

Ccsds401CarrierXmitTcPriority	 ::= ENUMERATED
{
	 yes                 	 	 (0)
,	 no                  	 	 (1)
}



-- This parameter configures and reports whether the symbol stream directly bpsk modulates
--  the transmit carrier such that the carrier is suppressed or directly bi-phase-L
--  modulates the carrier such that there is a remnant carrier or modulates a subcarrier
--  that in turn modulates the carrier. It can take on the following values:
-- - 'bpsk':
--  the carrier is bpsk modulated by the input data symbol stream; 
-- - 'direct': the
--  carrier is directly bi-phase-L modulated by the input data symbol stream;
-- - 'subcarrier':
--  the carrier modulating signal is the subcarrier which in turn is PSK modulated by
--  the to be radiated symbol stream.
-- For all three modulation options the parameter
--  specifies if the Doppler shift of the symbol stream shall be compensated and if
--  so, if a fixed offset (in 1/10000 Hz) shall be applied or if the symbol rate shall
--  be continuously updated (ramped) such that the spacecraft does not "see" any Doppler
--  shift of the symbol rate. Given that CCSDS 401.0 prescribes that subcarrier and
--  symbol rate have to be coherent, the subcarrier if applicable is Doppler shift compensated
--  in the same way as the symbol rate.
-- As applicable, the nominal symbol rate (in
--  1/10000 Hz) and nominal subcarrier frequency (in 1/10000 Hz) and the associated
--  modulation index (in 1/100 rad) are specified.
ccsds401CarrierXmitSymbolStreamModTypeParamOid	 OBJECT IDENTIFIER ::= { 1 3 112 4 4 2 1 20100 1 14 1 1 }

Ccsds401CarrierXmitSymbolStreamModType	 ::= SEQUENCE
{
	 symbolRateDopplerCompensation	 CHOICE
	 {
	 	 noCompensation      	 [0]	 	 NULL
,
	 	 -- The engineering unit of this parameter is 1/1000 Hertz.
	 	 staticOffset        	 [1]	 	 INTEGER  (-30000000 .. 30000000)
,
	 	 -- Given that CCSDS requires coherency of subcarrier and symbol clock, ramping of the
	 	 --  symbol rate implies that also the subcarrier frequency is ramped, in case a subcarrier
	 	 --  is used.
	 	 ramping             	 [2]	 	 NULL
	 }

,	 modType             	 CHOICE
	 {
	 	 bpsk                	 [0]	 	 SEQUENCE
	 	 {

	 	 	 -- The filter may be of the type Square Root Raised Cosine, 6-pole Butterworth, or equivalent
	 	 	 --  provided that the spectral mask limits are respected.
	 	 	 bandpassFilter      	 ENUMERATED
	 	 	 {
	 	 	 	 notApplied          	 	 (0)
	 	 	 ,	 applied             	 	 (1)
	 	 	 }

,	 	 	 bpskSymbolRateAndPcmFormat	 CHOICE
	 	 	 {
	 	 	 	 ccsds               	 [0]	 	 SEQUENCE
	 	 	 	 {
	 	 	 	 	 symbolRate          	 INTEGER  (100000000 | 200000000 | 400000000 | 800000000 | 1600000000 | 3200000000 | 6400000000 | 12800000000 | 25600000000 | 51200000000 | 102400000000 | 204800000000)
,	 	 	 	 	 pcmFormat           	 PcmFormat (biPhaseL)
	 	 	 	 }

,	 	 	 	 nonCcsds            	 [1]	 	 SEQUENCE
	 	 	 	 {
	 	 	 	 	 symbolRate          	 INTEGER  (100000000 .. 204800000000)
,	 	 	 	 	 pcmFormat           	 PcmFormat (biPhaseL | biPhaseM | biPhaseS)
	 	 	 	 }

	 	 	 }

	 	 }

,	 	 direct              	 [1]	 	 SEQUENCE
	 	 {

	 	 	 -- The engineering unit of this parameter is 1/100 radian
	 	 	 symbolStreamDirectModulationIndex	 INTEGER  (20 .. 140)
,	 	 	 directSymbolRateAndPcmFormat	 CHOICE
	 	 	 {
	 	 	 	 ccsds               	 [0]	 	 SEQUENCE
	 	 	 	 {
	 	 	 	 	 symbolRate          	 INTEGER  (400000000 | 800000000 | 1600000000 | 3200000000 | 6400000000 | 12800000000 | 25600000000)
,	 	 	 	 	 pcmFormat           	 PcmFormat (biPhaseL)
	 	 	 	 }

,	 	 	 	 nonCcsds            	 [1]	 	 SEQUENCE
	 	 	 	 {
	 	 	 	 	 symbolRate          	 INTEGER  (400000000 .. 25600000000)
,	 	 	 	 	 pcmFormat           	 PcmFormat (biPhaseL | biPhaseM | biPhaseS)
	 	 	 	 }

	 	 	 }

	 	 }

,	 	 subcarrier          	 [2]	 	 SEQUENCE
	 	 {
	 	 	 subcarrierFreqSymbolRateAndPcmFormat	 CHOICE
	 	 	 {
	 	 	 	 ccsds               	 [0]	 	 SEQUENCE
	 	 	 	 {
	 	 	 	 	 subcarrierFreqAndSymbolRate	 CHOICE
	 	 	 	 	 {
	 	 	 	 	 	 subcarrier8Khz      	 [0]	 	 SEQUENCE
	 	 	 	 	 	 {

	 	 	 	 	 	 	 -- The engineering unit of this parameter is 1/100000 Hertz.
	 	 	 	 	 	 	 subcarrierNominalFrequency	 INTEGER  (800000000)
,
	 	 	 	 	 	 	 -- The engineering unit of this parameter is 1/100000 Hertz.
	 	 	 	 	 	 	 nominalSymbolRate   	 INTEGER  (781250 | 1562500 | 3125000 | 6250000 | 12500000 | 25000000 | 50000000 | 100000000 | 200000000)
	 	 	 	 	 	 }

,	 	 	 	 	 	 subcarrier16Khz     	 [1]	 	 SEQUENCE
	 	 	 	 	 	 {

	 	 	 	 	 	 	 -- The engineering unit of this parameter is 1/100000 Hertz.
	 	 	 	 	 	 	 subcarrierNominalFrequency	 INTEGER  (1600000000)
,
	 	 	 	 	 	 	 -- The engineering unit of this parameter is 1/100000 Hertz
	 	 	 	 	 	 	 nominalSymbolRate   	 INTEGER  (781250 | 1562500 | 3125000 | 6250000 | 12500000 | 25000000 | 50000000 | 100000000 | 200000000 | 400000000)
	 	 	 	 	 	 }

	 	 	 	 	 }

,	 	 	 	 	 pcmFormat           	 PcmFormat (nrzL | nrzM)
	 	 	 	 }

,	 	 	 	 nonCcsds            	 [1]	 	 SEQUENCE
	 	 	 	 {

	 	 	 	 	 -- The engineering unit of this parameter is 1/100000 Hertz.
	 	 	 	 	 nominalSubcarrierFrequency	 INTEGER  (800000000 .. 1600000000)
,
	 	 	 	 	 -- The engineering unit of this parameter is 1/100000 Hertz.
	 	 	 	 	 nominalSymbolRate   	 CHOICE
	 	 	 	 	 {

	 	 	 	 	 	 -- The engineering unit of this element is 1/10000 symbols per second.
	 	 	 	 	 	 nonCoherent         	 [0]	 	 INTEGER  (781250 .. 400000000)
,
	 	 	 	 	 	 -- This element specifies the integer divisor of the subcarrier frequency for specifying
	 	 	 	 	 	 --  the symbol rate in symbols per second.
	 	 	 	 	 	 coherent            	 [1]	 	 INTEGER  (4 .. 2048)
	 	 	 	 	 }

,	 	 	 	 	 pcmFormat           	 PcmFormat (nrzL | nrzM | nrzS)
	 	 	 	 }

	 	 	 }

,
	 	 	 -- The engineering unit of this parameter is 1/100 radian.
	 	 	 subcarrierModIndex  	 INTEGER  (20 .. 140)
	 	 }

	 }

}



-- This parameter configures and reports the configured peak modulation index for the
--  ranging signal in 1/100 radians. If the ccsds401CarrierXmitSymbolStreamModType is
--  'bpsk', concurrent transmission of telecommands and ranging signals is not possible.
ccsds401CarrierXmitRngModIndexParamOid	 OBJECT IDENTIFIER ::= { 1 3 112 4 4 2 1 20100 1 15 1 1 }

-- The engineering unit of this parameter is 1/100 radian.
Ccsds401CarrierXmitRngModIndex	 ::= SEQUENCE
{

	 -- The engineering unit of this element is 1/100 radian.
	 duringAmbiguityResolution	 INTEGER  (0 .. 140)
,
	 -- The engineering unit of this element is 1/100 radian
	 afterAmbiguityResolution	 INTEGER  (0 .. 140)
}



-- This parameter reports the actual subcarrier frequency in 1/1000 Hz.  The fine resolution
--  is specified here as to enable reporting of the fine tuning of the subcarrier frequency
--  in cases where Doppler shift compensation is applied. In case that no subcarrier
--  is used (ccsds401CarrierXmitSymbolStreamModType ≠ 'subcarrier'), this parameter
--  shall report '0'.  
-- Note: The specified range is intended to also cover the case
--  of non-CCSDS missions. 
ccsds401CarrierXmitSubcarrierFreqParamOid	 OBJECT IDENTIFIER ::= { 1 3 112 4 4 2 1 20100 1 16 1 1 }

-- The engineering unit of this parameter is 1/10000 Hertz
Ccsds401CarrierXmitSubcarrierFreq	 ::= INTEGER  (0 .. 320000000)


-- This enumerated parameter configures and reports if the subcarrier is currently being
--  modulated by the TC symbol streaam and can take on two values:
-- - 'on': the subcarrier
--  is currently being modulated;
-- - 'off': the subcarrier is currently not being modulated.
-- In
--  case no subcarrier is used (ccsds401CarrierXmitSymbolStreamModType ≠ subcarrier'),
--  this parameter shall be flagged as undefined.
ccsds401CarrierXmitSubcarrierModParamOid	 OBJECT IDENTIFIER ::= { 1 3 112 4 4 2 1 20100 1 17 1 1 }

Ccsds401CarrierXmitSubcarrierMod	 ::= ENUMERATED
{
	 off                 	 	 (0)
,	 on                  	 	 (1)
}



-- This parameter reports the actual transmit link symbol rate in 1/10000 Hz, 
ccsds401CarrierXmitSymbolRateParamOid	 OBJECT IDENTIFIER ::= { 1 3 112 4 4 2 1 20100 1 18 1 1 }

-- The engineering unit of this parameter is 1/10000 Hertz.
Ccsds401CarrierXmitSymbolRate	 ::= INTEGER  (78125 .. 205100000000)


-- This event notifies any change of the ccsds401CarrierXmitResourceStat parameter.
ccsds401CarrierXmitResourceStatChangeEventOid	 OBJECT IDENTIFIER ::= { 1 3 112 4 4 2 1 20100 2 1 1 }




-- The event value reports the ccsds401CarrierXmitResourceStat value that applies since
--  the notified ccsds401CarrierXmitStatChange event occurred.
ccsds401CarrierXmitResourceStatChangeEventValueValueOid	 OBJECT IDENTIFIER ::= { 1 3 112 4 4 2 1 20100 2 1 1 1 }

Ccsds401CarrierXmitResourceStatChangeEventValue	 ::= Ccsds401CarrierXmitResourceStat


-- This directive permits setting of the controllable parameters of the Ccsds401SpaceLinkCarrierXmit
--  FR type. 
ccsds401CarrierXmitSetContrParamsDirectiveOid	 OBJECT IDENTIFIER ::= { 1 3 112 4 4 2 1 20100 3 1 1 }




-- The directive qualifier specifies the FR instance the directive shall act on and
--  contains a set of parameter identifier and parameter value pairs. To be valid, the
--  parameter identifier must reference a controllable parameter of the Ccsds401SpaceLinkCarrierXmit
--  FR and the parameter value must be of the same type as the parameter value that
--  shall be set.
-- 
ccsds401CarrierXmitContrParamIdsAndValuesQualifierOid	 OBJECT IDENTIFIER ::= { 1 3 112 4 4 2 1 20100 3 1 1 1 }

Ccsds401CarrierXmitContrParamIdsAndValues	 ::= DirectiveQualifier


-- This FR does not take any input. 
-- It provides the ranging signal to be radiated
--  to the spacecraft to the Ccsds401SpaceLinkCarrierXmit FR for modulation onto the
--  forward carrier.
-- It provides the timing information needed by the rngAndDopplerExtraction
--  FR.
-- 
rngXmitFrOid	 OBJECT IDENTIFIER ::= { 1 3 112 4 4 2 1 20101 }




-- This enumerated parameter reports the RngXmit FR resource status and can take on
--  four values:
-- - 'configured';
-- - 'operational';
-- - 'interrupted';
-- - 'halted'.
rngXmitResourceStatParamOid	 OBJECT IDENTIFIER ::= { 1 3 112 4 4 2 1 20101 1 1 1 1 }

RngXmitResourceStat 	 ::= ResourceStat


-- This enumerated parameter configures and reports if the ranging system is active
--  and can take on two values:
-- - 'enabled': the ranging system is presently active,
--  i.e., the ranging system is generating the ranging signal and modulating it on the
--  transmit carrier;
-- - 'disabled': the ranging system is presently not active as far
--  as the transmit link is concerned, i.e., no ranging signal is modulated on the transmit
--  carrier.
-- 
-- If rngXmitMod = 'enabled', the parameter also specifies if the ranging
--  shall be performed with the spacecraft or with the calibration translator in the
--  ranging calibration loop. In the latter case also the transponder ratio is specified
--  for the configuration of the calibration translator.
rngXmitModParamOid	 OBJECT IDENTIFIER ::= { 1 3 112 4 4 2 1 20101 1 2 1 1 }

RngXmitMod          	 ::= CHOICE
{
	 disabled            	 [0]	 	 NULL
,	 enabled             	 [1]	 	 CHOICE
	 {
	 	 tracking            	 [0]	 	 NULL
,	 	 calibrating         	 [1]	 	 CHOICE
	 	 {
	 	 	 transponderRatio221To240	 [0]	 	 SEQUENCE
	 	 	 {
	 	 	 	 transponderRatioNumerator	 INTEGER  (221)
,	 	 	 	 transponderRatioDenominator	 INTEGER  (240)
	 	 	 }

,	 	 	 transponderRatio749To880	 [1]	 	 SEQUENCE
	 	 	 {
	 	 	 	 transponderRatioNumerator	 INTEGER  (749)
,	 	 	 	 transponderRatioDenominator	 INTEGER  (880)
	 	 	 }

,	 	 	 transponderRatio221To900	 [2]	 	 SEQUENCE
	 	 	 {
	 	 	 	 transponderRatioNumerator	 INTEGER  (221)
,	 	 	 	 transponderRatioDenominator	 INTEGER  (900)
	 	 	 }

,	 	 	 transponderRatio765To240	 [3]	 	 SEQUENCE
	 	 	 {
	 	 	 	 transponderRatioNumerator	 INTEGER  (765)
,	 	 	 	 transponderRatioDenominator	 INTEGER  (240)
	 	 	 }

,	 	 	 transponderRatio221To880	 [4]	 	 SEQUENCE
	 	 	 {
	 	 	 	 transponderRatioNumerator	 INTEGER  (221)
,	 	 	 	 transponderRatioDenominator	 INTEGER  (880)
	 	 	 }

,	 	 	 transponderRatio749To240	 [5]	 	 SEQUENCE
	 	 	 {
	 	 	 	 transponderRatioNumerator	 INTEGER  (749)
,	 	 	 	 transponderRatioDenominator	 INTEGER  (240)
	 	 	 }

,	 	 	 transponderRatio749To3344	 [6]	 	 SEQUENCE
	 	 	 {
	 	 	 	 transponderRatioNumerator	 INTEGER  (749)
,	 	 	 	 transponderRatioDenominator	 INTEGER  (3344)
	 	 	 }

,	 	 	 transponderRatio3599To3344	 [7]	 	 SEQUENCE
	 	 	 {
	 	 	 	 transponderRatioNumerator	 INTEGER  (3599)
,	 	 	 	 transponderRatioDenominator	 INTEGER  (3344)
	 	 	 }

,	 	 	 transponderRatio3599To3360	 [8]	 	 SEQUENCE
	 	 	 {
	 	 	 	 transponderRatioNumerator	 INTEGER  (3599)
,	 	 	 	 transponderRatioDenominator	 INTEGER  (3360)
	 	 	 }

,	 	 	 transponderRatio749ToSet2652To2800	 [9]	 	 SEQUENCE
	 	 	 {
	 	 	 	 transponderRatioNumerator	 INTEGER  (749)
,	 	 	 	 transponderRatioDenominator	 INTEGER  (2652 | 2662 | 2678 | 2688 | 2704 | 2720 | 2736 | 2754 | 2772 | 2784 | 2800)
	 	 	 }

,	 	 	 transponderRatio221To2772	 [10]	 	 SEQUENCE
	 	 	 {
	 	 	 	 transponderRatioNumerator	 INTEGER  (221)
,	 	 	 	 transponderRatioDenominator	 INTEGER  (2772)
	 	 	 }

,	 	 	 transponderRatio221To2850	 [11]	 	 SEQUENCE
	 	 	 {
	 	 	 	 transponderRatioNumerator	 INTEGER  (221)
,	 	 	 	 transponderRatioDenominator	 INTEGER  (2850)
	 	 	 }

,	 	 	 transponderRatio749ToSet836To864	 [12]	 	 SEQUENCE
	 	 	 {
	 	 	 	 transponderRatioNumerator	 INTEGER  (749)
,	 	 	 	 transponderRatioDenominator	 INTEGER  (836 | 840 | 846 | 850 | 854 | 858 | 864)
	 	 	 }

	 	 }

	 }

}



-- This enumerated parameter configures and reports reports the type of ranging that
--  is being used. It can take on the following values:
-- - 'toneCode': the system performs
--  range measurements in accordance with ECSS-E-50-02A or similar;
-- - 'pseudoNoise':
--  the system performs range measurements in accordance with CCSDS 414.1-B-2.
-- In addition
--  it permits to choose the Doppler compensation applied to the  ranging signal on
--  the transmit carrier. It may be
-- - 'noCompensation';
-- - 'oneWay': the spacecraft
--  "sees" the nominal ranging signal;
-- - 'twoWay': the ESLT "sees" the nominal ranging
--  signal.
rngXmitRngTypeParamOid	 OBJECT IDENTIFIER ::= { 1 3 112 4 4 2 1 20101 1 3 1 1 }

RngXmitRngType      	 ::= SEQUENCE
{
	 dopplerCompensation 	 ENUMERATED
	 {
	 	 noCompensation      	 	 (0)
	 ,	 oneWay              	 	 (1)
	 ,	 twoWay              	 	 (2)
	 }

,	 rngType             	 CHOICE
	 {
	 	 toneCode            	 [0]	 	 SEQUENCE
	 	 {

	 	 	 -- The engineering unit of this parameter is Hertz.
	 	 	 toneFreq            	 INTEGER  (100000 .. 1500000)
,	 	 	 rngCodeLength       	 INTEGER  (1 .. 24)
,	 	 	 codeComponentAndToneXmitDuration	 SEQUENCE
	 	 	 {

	 	 	 	 -- The engineering unit of this element is second.
	 	 	 	 codeComponent       	 INTEGER  (1 .. 10000)
,	 	 	 	 toneOnly            	 CHOICE
	 	 	 	 {

	 	 	 	 	 -- The engineering unit of this element is second. The transmission of the code sequence
	 	 	 	 	 --  is restarted when either the toneOnlyDuration has expired or the RngXmit FR is notified
	 	 	 	 	 --  b y the RngAndDopplerExtraction FR that a range measurement has been completed.
	 	 	 	 	 --  
	 	 	 	 	 maxToneOnlyDuratiom 	 [0]	 	 INTEGER  (1 .. 100000)
,
	 	 	 	 	 -- The ranging system remains in tone-only mode until either tone lock is lost or the
	 	 	 	 	 --  ranging system is disabled.
	 	 	 	 	 unlimitedToneOnlyDuration	 [1]	 	 NULL
,
	 	 	 	 	 -- On occurence of an ambiguity resolution failure notified by the RngAndDopplerExtraction
	 	 	 	 	 --  FR the RngXmit FR can either be paused or the transmission of the code sequenmce
	 	 	 	 	 --  can be restarted.
	 	 	 	 	 ambiguityResolutionFailure	 [2]	 	 CHOICE
	 	 	 	 	 {

	 	 	 	 	 	 -- The parameter rngXmitMod is set to 'disabled'.
	 	 	 	 	 	 pauseRngXmit        	 [0]	 	 NULL
,
	 	 	 	 	 	 -- The transmission of the code sequence is restarted.
	 	 	 	 	 	 restartCodeSequence 	 [1]	 	 NULL
	 	 	 	 	 }

	 	 	 	 }

	 	 	 }

	 	 }

,	 	 pseudoNoise         	 [1]	 	 SEQUENCE
	 	 {
	 	 	 chipRate            	 CHOICE
	 	 	 {
	 	 	 	 ccsds               	 [0]	 	 CHOICE
	 	 	 	 {
	 	 	 	 	 i-is-2              	 [0]	 	 SEQUENCE
	 	 	 	 	 {
	 	 	 	 	 	 i                   	 INTEGER  (2)
,	 	 	 	 	 	 k                   	 INTEGER  (8 .. 10)
	 	 	 	 	 }

,	 	 	 	 	 k-is-6              	 [1]	 	 SEQUENCE
	 	 	 	 	 {
	 	 	 	 	 	 i                   	 INTEGER  (1 | 2 | 3 | 4 | 5 | 6 | 7 | 8 | 9 | 10 | 11 | 12 | 16 | 32 | 64)
,	 	 	 	 	 	 k                   	 INTEGER  (6)
	 	 	 	 	 }

	 	 	 	 }

,
	 	 	 	 -- The engineering unit of this element is chips per second.
	 	 	 	 nonCcsds            	 [1]	 	 INTEGER  (30000 .. 17000000)
	 	 	 }

,	 	 	 codeType            	 ENUMERATED
	 	 	 {
	 	 	 	 t2b                 	 	 (0)
	 	 	 ,	 t4b                 	 	 (1)
	 	 	 }

,
	 	 	 -- Positive means that positive input data advance the carrier phase.
	 	 	 modulationSense     	 CHOICE
	 	 	 {

	 	 	 	 -- The modulation sense is positive.
	 	 	 	 ccsds               	 [0]	 	 NULL
,
	 	 	 	 -- The modulation sense is negative.
	 	 	 	 nonCcsds            	 [1]	 	 NULL
	 	 	 }

	 	 }

	 }

}



-- This parameter reports the nominal PN ranging chip rate in Hertz which is given by
--  the transmitted carrier frequency and the parameters k and l (see the parameter
--  rngXmitRngType) and shall be calculated as specified in Table 3.1 of CCSDS 414.1.
-- 
-- 
rngXmitPnChipRateParamOid	 OBJECT IDENTIFIER ::= { 1 3 112 4 4 2 1 20101 1 4 1 1 }

-- The engineering unit of this parameter is chips per second.
RngXmitPnChipRate   	 ::= INTEGER  (30000 .. 17000000)


-- This event notifies any change of the rngXmitResourceStat parameter.
rngXmitResourceStatChangeEventOid	 OBJECT IDENTIFIER ::= { 1 3 112 4 4 2 1 20101 2 1 1 }




-- The event value reports the rngXmitResourceStat value that applies since the notified
--  rngXmitStatChange event occurred.
rngXmitResourceStatChangeEventValueValueOid	 OBJECT IDENTIFIER ::= { 1 3 112 4 4 2 1 20101 2 1 1 1 }

RngXmitResourceStatChangeEventValue	 ::= RngXmitResourceStat


-- This directive permits setting of the controllable parameters of the RngXmit FR type.
--  
rngXmitSetContrParamsDirectiveOid	 OBJECT IDENTIFIER ::= { 1 3 112 4 4 2 1 20101 3 1 1 }




-- The directive qualifier specifies the FR instance the directive shall act on and
--  contains a set of parameter identifier and parameter value pairs. To be valid, the
--  parameter identifier must reference a controllable parameter of the RngXmit FR and
--  the parameter value must be of the same type as the parameter value that shall be
--  set.
-- 
rngXmitContrParamIdsAndValuesQualifierOid	 OBJECT IDENTIFIER ::= { 1 3 112 4 4 2 1 20101 3 1 1 1 }

RngXmitContrParamIdsAndValues	 ::= DirectiveQualifier


-- The Ccsds401SpaceLinkCarrierRcpt FR accepts as input the carrier signal from the
--  Antenna 
-- FR. It provides the symbol stream demodulated from the physical channel
--  to the 
-- FlfSyncAndChnlDecode FR. It provides observables needed for the creation
--  of 
-- radiometric data to the RangeAndDopplerExtraction FR.
-- It provides the carrier
--  waveform to the DdorRawDataCollection FR and to the 
-- OpenLoopRxFormatter FR. 
ccsds401SpaceLinkCarrierRcptFrOid	 OBJECT IDENTIFIER ::= { 1 3 112 4 4 2 1 20300 }




-- This enumerated parameter reports on the csds401SpaceLinkCarrierRcpt resource status
--  and can take on four values:
-- - 'configured': the carrier reception equipment has
--  been configured and the antenna moved to point, but due to geometry or spacecraft
--  timeline, no carrier signal is expected to be seen at this time or the expected
--  LOS time has passed where again LOS may be due to geometry or due to the spacecraft
--  timeline;
-- - 'operational': the carrier reception is active, i.e., all receiving
--  equipment is in nominal condition, the expected AOS time has passed and the expected
--  LOS has not yet been reached;
-- - 'interrupted': a failure has been detected, e.g.
--  a receiver malfunction, that prevents the reception of the carrier signal;
-- - 'halted':
--  the carrier reception has been taken out of service, e.g. due to a power failure
--  affecting the carrier reception string.
ccsds401CarrierRcptResourceStatParamOid	 OBJECT IDENTIFIER ::= { 1 3 112 4 4 2 1 20300 1 1 1 1 }

Ccsds401CarrierRcptResourceStat	 ::= ResourceStat


-- This parameter configures and reports the name assigned to the physical channel being
--  received. This name is a Visible String which has a length of 1 to 32 characters.
ccsds401CarrierRcptPhysChnlNameParamOid	 OBJECT IDENTIFIER ::= { 1 3 112 4 4 2 1 20300 1 2 1 1 }

Ccsds401CarrierRcptPhysChnlName	 ::= VisibleString (SIZE( 1 .. 32)) 


-- This parameter configures and reports the carrier modulation type and the associated
--  parameters of the carrier being received. The following options are selectable:
-- -
--  'subcarrier': the symbol stream BPSK modulates a subcarrier which in turn phase
--  modulates the carrier;
-- - 'direct': the symbol stream directly bi-phase-L modulates
--  the carrier with a modulation index resulting in a remnant carrier.
-- - 'bpsk': the
--  symbol stream bpsk modulates the carrier which means that the carrier is suppressed.
-- -
--  'qpsk': the quadrature phase shift keying uses four phase constellatioin points
--  so that each constellation point represents two symbols of the modulating symbol
--  stream. The carrier is suppressed.
-- - 'oqpsk': as qpsk offset quadrature phase shift
--  keying uses four phase constellatioin points, but the modulation by the odd and
--  even symbol are offset by one symbol time which prevents the occurrence of 180°
--  phase shifts. 
-- - 'gmsk': the symbol stream is passed through a Gaussian filter
--  and then modulates the carrier by means of minimum-shift-keying. This suppresses
--  the carrier.
ccsds401CarrierRcptModTypeParamOid	 OBJECT IDENTIFIER ::= { 1 3 112 4 4 2 1 20300 1 3 1 1 }

Ccsds401CarrierRcptModType	 ::= CHOICE
{
	 subcarrier          	 [0]	 	 SEQUENCE
	 {
	 	 symbolRate          	 CHOICE
	 	 {
	 	 	 ccsdsSubcarrierFrequencySymbolRateRatio	 [0]	 	 INTEGER  (2 .. 1024)
,
	 	 	 -- The engineering unit of this element is 1/1000 symbols per second.
	 	 	 nonCcsdsAbsoluteSymbolRate	 [1]	 	 INTEGER  (1000 .. 32000000)
	 	 }

,	 	 subcarrierWaveform  	 ENUMERATED
	 	 {
	 	 	 square              	 	 (0)
	 	 ,	 sine                	 	 (1)
	 	 }

,
	 	 -- The engineering unit of this element is 1/100 radian.
	 	 modulationIndexTelemetry	 INTEGER  (1 .. 150)
,	 	 pcmFormat           	 PcmFormat (nrzL)
	 }

,	 direct              	 [1]	 	 SEQUENCE
	 {

	 	 -- The engineering unit of this parameter is 1/1000 symbols per second.
	 	 symbolRate          	 INTEGER  (8000000 .. 256000000)
,
	 	 -- The engineering unit of this parameter is 1/100 radian.
	 	 modulationIndexTelemetry	 INTEGER  (1 .. 150)
,	 	 pcmFormat           	 PcmFormat (biPhaseL)
	 }

,	 bpsk                	 [2]	 	 SEQUENCE
	 {

	 	 -- The engineering unit of this parameter is 1/1000 symbols per second.
	 	 symbolRate          	 INTEGER  (64000000 .. 20000000000)
,	 	 pcmFormat           	 PcmFormat (nrzS)
,
	 	 -- Enable or disable the square-root raised cosine matched filter depending on the filtering
	 	 --  applied on the spacecraft side.
	 	 matchedFilter       	 ENUMERATED
	 	 {
	 	 	 matchedFilterOff    	 	 (0)
	 	 ,	 matchedFilterOn     	 	 (1)
	 	 }

	 }

,
	 -- This element specifies the symbol rate in 1/1000 per second.
	 qpsk                	 [3]	 	 SEQUENCE
	 {

	 	 -- This element specifies the symbol rate in 1/1000 symbols per second
	 	 symbolRate          	 INTEGER  (1000 .. 20000000000)
,	 	 constellationConfiguration	 CHOICE
	 	 {

	 	 	 -- symbol assignment to I and Q channel and the mapping of IQ pairs to the carrier phase
	 	 	 --  complies with CCSDS 401
	 	 	 ccsds               	 [0]	 	 NULL
,	 	 	 nonCcsds            	 [1]	 	 SEQUENCE
	 	 	 {
	 	 	 	 symbolToIqMapping   	 CHOICE
	 	 	 	 {

	 	 	 	 	 -- This is as specifiied in CCSDS 401
	 	 	 	 	 evenSymbolOnIchannel	 [0]	 	 NULL
,	 	 	 	 	 evenSymbolOnQchannel	 [1]	 	 NULL
	 	 	 	 }

,	 	 	 	 symbolPairToPhaseAssignment	 SEQUENCE
	 	 	 	 {

	 	 	 	 	 -- Carrier phase in degrees
	 	 	 	 	 symbolPair00        	 INTEGER  (45 | 135 | 225 | 315)
,
	 	 	 	 	 -- Carrier phase in degrees
	 	 	 	 	 symbolPair01        	 INTEGER  (45 | 135 | 225 | 315)
,
	 	 	 	 	 -- Carrier phase in degrees
	 	 	 	 	 symbolPair10        	 INTEGER  (45 | 135 | 225 | 315)
,
	 	 	 	 	 -- Carrier phase in degrees
	 	 	 	 	 symbolPair11        	 INTEGER  (45 | 135 | 225 | 315)
	 	 	 	 }

	 	 	 }

	 	 }

,
	 	 -- Enable or disable the square-root raised cosine matched filter depending on the filtering
	 	 --  applied on the spacecraft side.
	 	 matchedFilter       	 ENUMERATED
	 	 {
	 	 	 matchedFilterOff    	 	 (0)
	 	 ,	 matchedFilterOn     	 	 (1)
	 	 }

	 }

,
	 -- This element specifies the symbol rate in 1/1000 symbol per second.
	 oqpsk               	 [4]	 	 SEQUENCE
	 {

	 	 -- This element specifies the symbol rate in 1/1000 symbols per second
	 	 symbolRate          	 INTEGER  (1000 .. 20000000000)
,	 	 constellationConfiguration	 CHOICE
	 	 {

	 	 	 -- symbol assignment to I and Q channel and the mapping of IQ pairs to the carrier phase
	 	 	 --  complies with CCSDS 401
	 	 	 ccsds               	 [0]	 	 NULL
,	 	 	 nonCcsds            	 [1]	 	 SEQUENCE
	 	 	 {
	 	 	 	 symbolToIqMapping   	 CHOICE
	 	 	 	 {

	 	 	 	 	 -- This is as specifiied in CCSDS 401
	 	 	 	 	 evenSymbolOnIchannel	 [0]	 	 NULL
,	 	 	 	 	 evenSymbolOnQchannel	 [1]	 	 NULL
	 	 	 	 }

,	 	 	 	 symbolPairToPhaseAssignment	 SEQUENCE
	 	 	 	 {

	 	 	 	 	 -- Carrier phase in degrees
	 	 	 	 	 symbolPair00        	 INTEGER  (45 | 135 | 225 | 315)
,
	 	 	 	 	 -- Carrier phase in degrees
	 	 	 	 	 symbolPair01        	 INTEGER  (45 | 135 | 225 | 315)
,
	 	 	 	 	 -- Carrier phase in degrees
	 	 	 	 	 symbolPair10        	 INTEGER  (45 | 135 | 225 | 315)
,
	 	 	 	 	 -- Carrier phase in degrees
	 	 	 	 	 symbolPair11        	 INTEGER  (45 | 135 | 225 | 315)
	 	 	 	 }

	 	 	 }

	 	 }

,
	 	 -- Enable or disable the matched filter depending on the filtering applied on the spacecraft
	 	 --  side. The filter type may be of type Square Root Raised Cosine α = 0.5 or Butterworth
	 	 --  6 poles, BT = 0.5 or similar bandpass filters with BT ≤ 0.5. 
	 	 matchedFilter       	 ENUMERATED
	 	 {
	 	 	 matchedFilterOff    	 	 (0)
	 	 ,	 matchedFilterOn     	 	 (1)
	 	 }

	 }

,	 gmsk                	 [5]	 	 SEQUENCE
	 {

	 	 -- This element specifies the symbol rate in 1/1000 symbol per second.
	 	 symbolRate          	 INTEGER  (1000 .. 20000000000)
,
	 	 -- The scaling factor of this parameter is 1/100
	 	 bandwidthSymbolPeriodProduct	 INTEGER  (0 .. 1000)
,	 	 concurrentGmskAndPnRng	 ENUMERATED
	 	 {
	 	 	 yes                 	 	 (0)
	 	 ,	 no                  	 	 (1)
	 	 }

	 }

}



-- This parameter configures and reports the channel (polarization) that shall be used
--  as input for reception and demodulation. It can take on the following values:
-- -
--  'lhc';
-- - 'rhc';
-- - 'autoHysteresis';
-- - 'combining'.
-- If 'autoHysteresis' is chosen,
--  the parameter specifies how much larger in 1/10 dB the power observed for the unselected
--  polarization must be before a switch-over to the polarization with the stronger
--  signal is performed.
-- 'combining' means that diversity combining of the lhc and
--  rhc channels is performed. This is only permissible for modulation schemes with
--  remnant carrier. This element of the choice specifies the bandwidth in Hertz within
--  which the the two signals shall be combined.
ccsds401CarrierRcptPolarizationParamOid	 OBJECT IDENTIFIER ::= { 1 3 112 4 4 2 1 20300 1 4 1 1 }

Ccsds401CarrierRcptPolarization	 ::= CHOICE
{
	 lhc                 	 [0]	 	 NULL
,	 rhc                 	 [1]	 	 NULL
,
	 -- The engineering unit of this element is 1/10 dB.
	 autoHysteresis      	 [2]	 	 INTEGER  (0 .. 100)
,
	 -- The enginnering unit of this element is Hertz.
	 combiningBwdth      	 [3]	 	 INTEGER  (10 .. 100000)
}



-- This parameter reports (after acquisition of signal) the power ratio of the signal
--  received with left hand circular (LHC) polarization and the signal received with
--  the orthogonal, i.e., right hand circular (RHC) polarization. If the angle reported
--  is 0 degrees, then the full power is received via the LHC channel. At 45 degrees,
--  the power in the LHC and RHC channels is equal, as if the input signal were linearly
--  polarized. At 90 degrees, the full power is received with RHC polarization.
-- Only
--  stations supporting concurrent reception of LHC and RHC polarization provide this
--  information. When this is not possible or the station is configured to use a single
--  channel only, this parameter shall be flagged as unavailable. 
ccsds401CarrierRcptPolarizationAngleParamOid	 OBJECT IDENTIFIER ::= { 1 3 112 4 4 2 1 20300 1 5 1 1 }

-- The engineering unit of this parameter is degree.
Ccsds401CarrierRcptPolarizationAngle	 ::= INTEGER  (0 .. 90)


-- This parameter configures and reports the expected level of the received signal in
--  dBm as observed at the LNA input. It shall be the total signal power so that the
--  same parameter specification applies regardless of the modulation scheme. 
ccsds401CarrierRcptExpectedSignalLevelParamOid	 OBJECT IDENTIFIER ::= { 1 3 112 4 4 2 1 20300 1 6 1 1 }

-- The engineering unit of this parameter is dBm
Ccsds401CarrierRcptExpectedSignalLevel	 ::= INTEGER  (-250 .. -30)


-- This parameter reports the difference between the actual and the predicted signal
--  level of the received signal as observed at the LNA input in 1/10 dB (actaul value
--  minus predicted value). 
ccsds401CarrierRcptSignalLevelResidualParamOid	 OBJECT IDENTIFIER ::= { 1 3 112 4 4 2 1 20300 1 7 1 1 }

-- The engineering unit of this parameter is 1/10 dB
Ccsds401CarrierRcptSignalLevelResidual	 ::= INTEGER  (-500 .. 500)


-- This parameter reports the system noise temperature in K derived from the noise density
--  observed at the receiver input. As such, it takes into account all contributions
--  to the noise temperature such as antenna microwave components, atmospheric noise
--  and cosmic microwave background noise. The noise temperature varies with weather
--  conditions and antenna elevation due to variation of the path length through the
--  atmosphere and ground noise received by the antenna side lobes.
ccsds401CarrierRcptSystemNoiseTemperatureParamOid	 OBJECT IDENTIFIER ::= { 1 3 112 4 4 2 1 20300 1 8 1 1 }

-- The engineering unit of this parameter is Kelvin.
Ccsds401CarrierRcptSystemNoiseTemperature	 ::= INTEGER  (1 .. 1000)


-- This parameter configures and reports the nominal frequency of the received carrier
--  disregarding any Doppler shift.
-- 
ccsds401CarrierRcptNominalFreqParamOid	 OBJECT IDENTIFIER ::= { 1 3 112 4 4 2 1 20300 1 9 1 1 }

-- The engineering unit of this parameter is Hertz.
Ccsds401CarrierRcptNominalFreq	 ::= INTEGER  (2200000000 .. 32300000000)


-- This parameter configures and reports the frequency range in Hz centered around the
--  ccsds401CarrierRcptNominalFreq, possibly corrected for the expected Doppler offset,
--  in which the receiver shall search for the carrier signal. This parameter is also
--  valid in case of a suppressed carrier modulation scheme.
-- 
ccsds401CarrierRcptFreqSearchRangeParamOid	 OBJECT IDENTIFIER ::= { 1 3 112 4 4 2 1 20300 1 10 1 1 }

-- The engineering unit of this parameter is Hertz.
Ccsds401CarrierRcptFreqSearchRange	 ::= INTEGER  (0 .. 1500000)


-- This enumerated parameter configures and reports for which condition the Doppler
--  predicts have been calculated. It can take on four values:
-- - none: no information
--  regarding the expected Doppler shift is available and therefore the nominal frequency
--  is used;
-- - 1-way: this mode will be used when the spacecraft is not locked to a
--  forward link signal or while the spacecraft transponder is commanded to non-coherent
--  mode or when the spacecraft receiver is in 'coherency enabled' mode and the forward
--  link carrier frequency is ramped such that the Doppler on the forward link is compensated,
--  i.e., the spacecraft always 'sees' the nominal forward link frequency; in this case
--  it does not matter if the forward link is radiated by the same station as the one
--  that is receiving the return link or a different station; 
-- - 2-way: this mode is
--  applied when the spacecraft receiver is commanded to 'coherency enabled' mode and
--  the station that is receiving the return link also radiates the forward link, the
--  latter at a constant frequency;
-- - 3-way: this mode is applied when the spacecraft
--  receiver is in 'coherency enabled' mode and a station different from the one receiving
--  the return link is radiating the forward link signal at a known constant frequency.
ccsds401CarrierRcptPredictModeParamOid	 OBJECT IDENTIFIER ::= { 1 3 112 4 4 2 1 20300 1 11 1 1 }

Ccsds401CarrierRcptPredictMode	 ::= ENUMERATED
{
	 none                	 	 (1)
,	 oneWay              	 	 (2)
,	 twoWay              	 	 (3)
,	 threeWay            	 	 (4)
}



-- This parameter configures and reports the dual-sided tracking loop bandwidth in tenth
--  Hz of the receiver and the duration in seconds within which the bandwidth reduction
--  to a newly commanded loop bandwidth shall be reached. This gradual change of the
--  loop bandwidth is intended to avoid loss of lock. The duration for the gradual bandwidth
--  change can be set to 'auto' or set to a specific duration. If the duration is set
--  to 0, the newly commanded bandwidth is applied immediately. 
ccsds401CarrierRcptTrackingLoopBwdthParamOid	 OBJECT IDENTIFIER ::= { 1 3 112 4 4 2 1 20300 1 12 1 1 }

Ccsds401CarrierRcptTrackingLoopBwdth	 ::= SEQUENCE
{

	 -- The engineering unit of this element is 1/10 Hertz.
	 trackingLoopBwdth   	 INTEGER  (1 .. 30000)
,
	 -- The engineering unit of this element is second.
	 loopBwdthChangeDuration	 CHOICE
	 {

	 	 -- The time during which the bandwidth is gradually changed to the newly set value is
	 	 --  chosen automatically.
	 	 auto                	 [0]	 	 NULL
,
	 	 -- The engineering unit of this element is second. If it is set to 0, the newly commanded
	 	 --  bandwidth is applied immediately.
	 	 bwdthChangeDuration 	 [1]	 	 INTEGER  (0 .. 100)
	 }

}



-- This enumerated parameter configures and reports the order of the carrier tracking
--  loop. It can take on the following values:
-- - 'first order': such loop is hardly
--  ever used because it has a static phase error even in case of a constant carrier
--  frequency being received;
-- - 'second order': this is the most commonly used loop
--  as it has no static phase error for a constant carrier frequency being received;
-- -
--  'third order': such configuration may have to be used in case of high Doppler rates,
--  as such loop has no static phase error even when the carrier frequency being received
--  is changing because of the given Doppler rate, but initial acquisition is more difficult
--  with such loop. 
ccsds401CarrierRcptOrderOfLoopParamOid	 OBJECT IDENTIFIER ::= { 1 3 112 4 4 2 1 20300 1 13 1 1 }

Ccsds401CarrierRcptOrderOfLoop	 ::= ENUMERATED
{
	 firstOrder          	 	 (0)
,	 secondOrder         	 	 (1)
,	 thirdOrder          	 	 (2)
}



-- This parameter reports the lock status for the carrier, and, if applicable, for the
--  subcarrier, and for the symbol stream.
ccsds401CarrierRcptLockStatParamOid	 OBJECT IDENTIFIER ::= { 1 3 112 4 4 2 1 20300 1 14 1 1 }

Ccsds401CarrierRcptLockStat	 ::= LockStat


-- This parameter reports the signal-to-noise ratio in the carrier tracking loop. It
--  is derived from the carrier-loop-phase-error-std-deviation (std) as follows: SNR
--  in 1/100 dB is given by 1000 log (2/(2PI std)^2) where log is to the base of 10.
--  The carrier loop phase error standard deviation (or rms value) in rad over n samples,
--  i.e. the sum of (Ei - M)^2 for i = 1 .. n is calculated, then divided by n and then
--  the square root taken.
-- A given implementation shall specify the number of samples
--  used to calculate this parameter. This shall be recorded in the Service Agreement.
ccsds401CarrierRcptCarrierLoopSnrParamOid	 OBJECT IDENTIFIER ::= { 1 3 112 4 4 2 1 20300 1 15 1 1 }

-- The engineering unit of this parameter is 1/100 dB
Ccsds401CarrierRcptCarrierLoopSnr	 ::= INTEGER  (-2800 .. 10000)


-- This parameter reports the mean value of the phase error in 1/100 radians in the
--  carrier tracking loop by summing up the loop errors Ei over a period of n samples
--  and then dividing the sum by n. The mean M should be zero unless the loop is subject
--  to a static phase error.
-- A given implementation shall specify the number of samples
--  used to calculate this paramter. This shall be recorded in the Service Agreement.
ccsds401CarrierRcptCarrierLoopMeanPhaseErrorParamOid	 OBJECT IDENTIFIER ::= { 1 3 112 4 4 2 1 20300 1 16 1 1 }

-- The engineering unit of this parameter is 1/100 radian.
Ccsds401CarrierRcptCarrierLoopMeanPhaseError	 ::= INTEGER  (-629 .. 629)


-- This parameter reports the observed carrier frequency being received in Hz. This
--  parameter therefore varies with the Doppler shift induced by the radial velocity
--  of the transmitting antenna (in general the spacecraft) relative to the receiving
--  antenna (in general the ESLT antenna). In 1-way mode, the Doppler shift applies
--  only once, but also the onboard oscillator drift affects the observed return link
--  carrier frequency. In 2-way mode in combination with a constant forward link frequency,
--  the Doppler shift approximately doubles with respect to the 1-way case, but the
--  contribution of the onboard oscillator drift is eliminated.
ccsds401CarrierRcptActualFreqParamOid	 OBJECT IDENTIFIER ::= { 1 3 112 4 4 2 1 20300 1 17 1 1 }

-- The engineering unit of the parameter is Hertz.
Ccsds401CarrierRcptActualFreq	 ::= INTEGER  (2199700000 .. 38500000000)


-- This parameter reports the observed frequency offset in Hz of the carrier being received
--  with respect to the nominal carrier frequency. As such it reports on the oscillator
--  drift (in case of 1-way operation) on the transmitting side plus the Doppler shift
--  induced by the radial velocity between the transmitting and receiving antennas.
--  In 2-way mode, the effect of the oscillator drift at the transmitting end is eliminated.
--  In combination with a constant forward link frequency, the Doppler shift approximately
--  doubles compared to the 1-way case.
ccsds401CarrierRcptFreqOffsetParamOid	 OBJECT IDENTIFIER ::= { 1 3 112 4 4 2 1 20300 1 18 1 1 }

-- The engineering unit of this parameter is Hertz.
Ccsds401CarrierRcptFreqOffset	 ::= INTEGER  (-5000000 .. 5000000)


-- This parameter reports the Doppler offset standard deviation in Hz over n samples.
--  Each sample Si is the difference between the actual return link frequency and the
--  predicted return link frequency where the predict takes into account the expected
--  Doppler shift. Based on these samples, the mean Doppler offset M is calculated by
--  forming the sum of n samples Si and dividing it by n. Then the sum of (Si - M)^2
--  for i = 1 .. n is calculated, divided by n and then the square root taken.
-- A given
--  implementation shall specify the number of samples used to calculate this paramter.
--  This shall be recorded in the Service Agreement.
ccsds401CarrierRcptDopplerStdDeviationParamOid	 OBJECT IDENTIFIER ::= { 1 3 112 4 4 2 1 20300 1 19 1 1 }

-- The engineering unit of this parameter is Hertz.
Ccsds401CarrierRcptDopplerStdDeviation	 ::= INTEGER  (0 .. 5000000)


-- This parameter reports the frequency in Hz of the to be transmitted carrier that
--  corresponds to the non-coherent frequency of the received carrier divided by the
--  transponder turnaround ratio in the Doppler free case. The spacecraft is expected
--  to lock on the transmitted carrier, when it 'sees' this frequency. 
ccsds401CarrierRcptBestLockFreqParamOid	 OBJECT IDENTIFIER ::= { 1 3 112 4 4 2 1 20300 1 20 1 1 }

-- The engineering unit of this parameter is Hertz.
Ccsds401CarrierRcptBestLockFreq	 ::= INTEGER  (2024956000 .. 40501863000)


-- This parameter configures and reports the nominal subcarrier frequency in 1/1000
--  Hz. If the applicable modulation scheme does not use a subcarrier, this parameter
--  shall be flagged as 'undefined'. 
-- Except if ccsds401CarrierRcptPredictMode is set
--  to 'none', the demudulator shall however be configured to the nominal subcarrier
--  frequency corrected for the 1-way Doppler offset because in general the subcarrier
--  is generated by the transmitting end, i.e., the spacecraft, independently of a carrier
--  received by the spacecraft and therefore subject to the 1-way Doppler shift.
ccsds401CarrierRcptNominallSubcarrierFreqParamOid	 OBJECT IDENTIFIER ::= { 1 3 112 4 4 2 1 20300 1 21 1 1 }

-- The engineering unit of this parameter is 1/1000 Hertz.
Ccsds401CarrierRcptNominallSubcarrierFreq	 ::= INTEGER  (2000000 .. 4000000000)


-- This parameter reports the actually received subcarrier frequency in 1/1000 Hz, i.e.,
--  this parameter reflects the Doppler shift of the subcarrier frequency. If the applicable
--  modulation scheme does not use a subcarrier, this parameter shall be flagged as
--  'undefined'.
ccsds401CarrierRcptActualSubcarrierFreqParamOid	 OBJECT IDENTIFIER ::= { 1 3 112 4 4 2 1 20300 1 22 1 1 }

-- The engineering unit of this parameter is 1/1000 Hertz.
Ccsds401CarrierRcptActualSubcarrierFreq	 ::= INTEGER  (2000000 .. 4000000000)


-- This parameter configures and reports the subcarrier demodulator loop bandwidth expressed
--  as dual-sided subcarrier loop bandwidth to subcarrier frequency ratio. If the applicable
--  modulation scheme does not use a subcarrier, this parameter shall be flagged as
--  undefined.
ccsds401CarrierRcptSubcarrierDemodLoopBwdthParamOid	 OBJECT IDENTIFIER ::= { 1 3 112 4 4 2 1 20300 1 23 1 1 }

Ccsds401CarrierRcptSubcarrierDemodLoopBwdth	 ::= REAL (1E-5 .. 1E-1)


-- This parameter reports the mean value of the phase error in 1/100 radians in the
--  subcarrier tracking loop by summing up the loop errors Ei over a period of n samples
--  and then dividing the sum by n. The mean M should be zero unless the loop is subject
--  to a static phase error.
-- A given implementation shall specify the number of samples
--  used to calculate this paramter. This shall be recorded in the Service Agreement.
ccsds401CarrierRcptSubcarrierLoopMeanPhaseErrorParamOid	 OBJECT IDENTIFIER ::= { 1 3 112 4 4 2 1 20300 1 24 1 1 }

-- The engineering unit of this parameter is 1/100 radian
Ccsds401CarrierRcptSubcarrierLoopMeanPhaseError	 ::= INTEGER  (-629 .. 629)


-- This parameter reports the subcarrier to carrier power ratio expressed in 1/100 dBc.
--  If the applicable modulation scheme does not use a subcarrier, this parameter shall
--  be flagged as 'undefined'.
ccsds401CarrierRcptSubcarrierLevelEstimateParamOid	 OBJECT IDENTIFIER ::= { 1 3 112 4 4 2 1 20300 1 25 1 1 }

-- The engineering unit of this parameter is 1/100 dBc.
Ccsds401CarrierRcptSubcarrierLevelEstimate	 ::= INTEGER  (-20000 .. 0)


-- This parameter configures and reports the nominal received symbol stream rate in
--  1/1000 symbols/second. 
-- Except if ccsds401CarrierRcptPredictMode is set to 'none',
--  the demudulator shall however be configured to the nominal symbol rate corrected
--  for the 1-way Doppler offset because in general the symbol clock is generated by
--  the transmitting end, i.e., the spacecraft, independently of a carrier received
--  by the spacecraft and therefore subject to the 1-way Doppler shift.
ccsds401CarrierRcptNominalSymbolRateParamOid	 OBJECT IDENTIFIER ::= { 1 3 112 4 4 2 1 20300 1 26 1 1 }

-- The engineering unit of this parameter is 1/1000 symbols per second.
Ccsds401CarrierRcptNominalSymbolRate	 ::= INTEGER  (4000 .. 160000000000)


-- This parameter reports the actually received symbol stream rate in 1/1000 symbols/second,
--  i.e., this parameter reflects the Doppler shift of the symbol rate.
ccsds401CarrierRcptActualSymbolRateParamOid	 OBJECT IDENTIFIER ::= { 1 3 112 4 4 2 1 20300 1 27 1 1 }

-- The engineering unit of this parameter is 1/1000 symbols per second.
Ccsds401CarrierRcptActualSymbolRate	 ::= INTEGER  (4000 .. 160000000000)


-- This parameter configures and reports the symbol synchronizer loop bandwidth expressed
--  as dual-sided symbol synchronizer loop bandwidth to symbol rate ratio. 
ccsds401CarrierRcptSymbolSynchronizerLoopBwdthParamOid	 OBJECT IDENTIFIER ::= { 1 3 112 4 4 2 1 20300 1 28 1 1 }

Ccsds401CarrierRcptSymbolSynchronizerLoopBwdth	 ::= REAL (1E-5 .. 1E-2)


-- This parameter reports the mean value of the phase error in 1/100 radians in the
--  symbol tracking loop by summing up the loop errors Ei over a period of n samples
--  and then dividing the sum by n. The mean M should be zero unless the loop is subject
--  to a static phase error.
-- A given implementation shall specify the number of samples
--  used to calculate this paramter. This shall be recorded in the Service Agreement.
ccsds401CarrierRcptSymbolLoopMeanPhaseErrorParamOid	 OBJECT IDENTIFIER ::= { 1 3 112 4 4 2 1 20300 1 29 1 1 }

-- The engineering unit of this parameter is 1/100 radian
Ccsds401CarrierRcptSymbolLoopMeanPhaseError	 ::= INTEGER  (-629 .. 629)


-- This parameter configures and reports the expected symbol energy over noise density
--  ratio (Es/No) in 1/100 dB. Depending on the equipment, the value may be used to
--  optimize carrier acquisition and lock detection in particular for very low values
--  (e.g. - 2 dB) as they may be encountered for turbo coding with coding rates > 1/2.
--  
ccsds401CarrierRcptExpectedEsOverNoParamOid	 OBJECT IDENTIFIER ::= { 1 3 112 4 4 2 1 20300 1 30 1 1 }

-- The engineering unit of this parameter is 1/100 dB.
Ccsds401CarrierRcptExpectedEsOverNo	 ::= INTEGER  (-1000 .. 60000)


-- This parameter reports the difference in 1/10 db between the expected symbol energy
--  over noise density ratio (Es/No) and the actually observed Es/No). The algorithms
--  used to calculate the observed Es/No tend to saturate at a certain Es/No level so
--  that the reported residual may correspond to an observed Es/No that is significantly
--  lower than expected. However, this saturation happens at levels that are so high
--  that the telemetry is anyway virtually error free. 
-- It also reports the distribution
--  of the soft symbols in percent. For each symbol the deviation from the perfect +1
--  and -1 as visible from the soft bits is normalized to +/- 50%. The observed deviation
--  is summed and devided by the number of samples taken. 
-- The duration used for averaging
--  the values reported by the ccsds401CarrierRcptEsOverNoResidualAndSoftSymbolDistribution
--  parameter should be documented in the Service Agreement. 
ccsds401CarrierRcptEsOverNoResidualAndSoftSymbolDistributionParamOid	 OBJECT IDENTIFIER ::= { 1 3 112 4 4 2 1 20300 1 31 1 1 }

Ccsds401CarrierRcptEsOverNoResidualAndSoftSymbolDistribution	 ::= SEQUENCE
{

	 -- The engineering unit of this element is 1/10 dB
	 esOverNoResidual    	 INTEGER  (-500 .. 500)
,
	 -- This element is reported in percent
	 softBitDistribution 	 INTEGER  (-50 .. 50)
}



-- This event notifies any change of the ccsds401CarrierRcptResourceStat.
ccsds401CarrierRcptResourceStatChangeEventOid	 OBJECT IDENTIFIER ::= { 1 3 112 4 4 2 1 20300 2 1 1 }




-- The event value reports the ccsds401CarrierRcptResourceStat value that applies since
--  the notified ccsds401CarrierRcptResourceSatChange event has occurred.
ccsds401CarrierRcptResourceStatChangeEventValueValueOid	 OBJECT IDENTIFIER ::= { 1 3 112 4 4 2 1 20300 2 1 1 1 }

Ccsds401CarrierRcptResourceStatChangeEventValue	 ::= Ccsds401CarrierRcptResourceStat


-- This event notifies any change of the lock status occurring when receiving or trying
--  to acquire the to be received carrier and reports the lock status as given since
--  the occurrence of the event.
ccsds401CarrierRcptLockStatChangeEventOid	 OBJECT IDENTIFIER ::= { 1 3 112 4 4 2 1 20300 2 2 1 }




-- The event value reports the lock status as given since the occurrence of the ccsds401CarrierRcptLockStatChange
--  event. It should be noted that loss of carrier lock implies loss of subcarrier lock
--  if a subcarrier is used and loss of symbol lock. Only the loss of carrier lock is
--  reported in this case. Loss of subcarrier lock, if a subcarrier is used, implies
--  loss of symbol lock. 
ccsds401CarrierRcptLockStatChangeEventValueValueOid	 OBJECT IDENTIFIER ::= { 1 3 112 4 4 2 1 20300 2 2 1 1 }

Ccsds401CarrierRcptLockStatChangeEventValue	 ::= Ccsds401CarrierRcptLockStat


-- This directive permits setting of the controllable parameters of the Ccsds401SpaceLinkCarrierRcpt
--  FR type. 
ccsds401CarrierRcptSetContrParamsDirectiveOid	 OBJECT IDENTIFIER ::= { 1 3 112 4 4 2 1 20300 3 1 1 }




-- The directive qualifier specifies the FR instance the directive shall act on and
--  contains a set of parameter identifier and parameter value pairs. To be valid, the
--  parameter identifier must reference a controllable parameter of the Ccsds401SpaceLinkCarrierRcpt
--  FR and the parameter value must be of the same type as the parameter value that
--  shall be set.
-- 
ccsds401SpaceLinkCarrierRcptContrParamIdsAndValuesQualifierOid	 OBJECT IDENTIFIER ::= { 1 3 112 4 4 2 1 20300 3 1 1 1 }

Ccsds401SpaceLinkCarrierRcptContrParamIdsAndValues	 ::= DirectiveQualifier


-- The RngAndDopplerExtraction FR accepts as input the timing information from the RngXmit
--  FR and the range and Doppler data from the Ccsds401SpaceLinkCarrierRcpt FR.
-- It
--  provides range and Doppler observables to the TdmSegmentGen FR and to the NonValRmDataCollection
--  FR.
rngAndDopplerExtractionFrOid	 OBJECT IDENTIFIER ::= { 1 3 112 4 4 2 1 20301 }




-- This enumerated parameter reports the rngAndDopplerExtractionResourceStat and can
--  take on four values:
-- - 'configured';
-- - 'operational';
-- - 'interrupted';
-- - 'halted'.
rngAndDopplerExtractionResourceStatParamOid	 OBJECT IDENTIFIER ::= { 1 3 112 4 4 2 1 20301 1 1 1 1 }

RngAndDopplerExtractionResourceStat	 ::= ResourceStat


-- This parameter configures and reports if the ranging signal acquisition shall be
--  presteered in accordance with the expected Doppler shift.
rngAndDopplerExtractionPresteeringParamOid	 OBJECT IDENTIFIER ::= { 1 3 112 4 4 2 1 20301 1 2 1 1 }

RngAndDopplerExtractionPresteering	 ::= ENUMERATED
{
	 dopplerPresteeringOff	 	 (0)
,	 dopplerPresteeringOn	 	 (1)
}



-- This parameter reports the difference between actual and the predicted ranging signal
--  power to noise density ratio expressed in 1/10 dB (actual value minus predicted
--  value).
rngAndDopplerExtractionRngPowerOverNoResidualParamOid	 OBJECT IDENTIFIER ::= { 1 3 112 4 4 2 1 20301 1 3 1 1 }

-- The engineering unit of this parameter is 1/10 dB.
RngAndDopplerExtractionRngPowerOverNoResidual	 ::= INTEGER  (-1000 .. 1000)


-- This parameter reports, in 1/1000 Hz, the dual sided bandwidth of the ranging tracking
--  loop. 
rngAndDopplerExtractionRngLoopBwdthParamOid	 OBJECT IDENTIFIER ::= { 1 3 112 4 4 2 1 20301 1 4 1 1 }

-- The engineering unit of this parameter is 1/1000 Hz
RngAndDopplerExtractionRngLoopBwdth	 ::= INTEGER  (1 .. 30000)


-- This parameter configures and reports the expected ranging signal power to noise
--  spectral density ratio within the ranging tracking loop bandwidth in 1/10 dB.
rngAndDopplerExtractionPredictedRngLoopSnrParamOid	 OBJECT IDENTIFIER ::= { 1 3 112 4 4 2 1 20301 1 5 1 1 }

-- The engineering unit of this parameter is 1/10 dB.
RngAndDopplerExtractionPredictedRngLoopSnr	 ::= INTEGER  (0 .. 400)


-- This parameter reports the probability in percent of successful ranging signal acquisition
--  derived from the predicted Pr/No and the configured ranging loop bandwidth, i.e.
--  from the predicted ranging loop SNR (see parameter rngAndDopplerExtractionPredictedRngLoopSnr).
rngAndDopplerExtractionRngSignalAcquisitionProbabilityParamOid	 OBJECT IDENTIFIER ::= { 1 3 112 4 4 2 1 20301 1 6 1 1 }

-- The engineering unit of this parameter is percent.
RngAndDopplerExtractionRngSignalAcquisitionProbability	 ::= INTEGER  (0 .. 100)


-- This parameter configures and reports the duration of the period in milliseconds
--  during which the ranging tracking loop is operated in open-loop mode.
rngAndDopplerExtractionOpenLoopTimeParamOid	 OBJECT IDENTIFIER ::= { 1 3 112 4 4 2 1 20301 1 7 1 1 }

-- The engineering unit of this parameter is 1/1000 second.
RngAndDopplerExtractionOpenLoopTime	 ::= INTEGER  (1 .. 10000)


-- This parameter configures and reports the duration of the period in milliseconds
--  after closure of the ranging tracking loop until loop lock is reported and range
--  measurements can start. This allows any residual loop transient to die away. 
rngAndDopplerExtractionLoopSettlingTimeParamOid	 OBJECT IDENTIFIER ::= { 1 3 112 4 4 2 1 20301 1 8 1 1 }

-- The engineering unit of this parameter is 1/1000 second.
RngAndDopplerExtractionLoopSettlingTime	 ::= INTEGER  (1 .. 10000)


-- This enumerated value reports the tone respectively PN chip loop lock status. It
--  can take on two values:
-- - 'not locked'.
-- - 'locked'.
rngAndDopplerExtractionLoopLockStatParamOid	 OBJECT IDENTIFIER ::= { 1 3 112 4 4 2 1 20301 1 9 1 1 }

RngAndDopplerExtractionLoopLockStat	 ::= ENUMERATED
{
	 notLocked           	 	 (0)
,	 locked              	 	 (1)
}



-- This parameter reports the tone / pn-chip power to carrier power ratio expressed
--  in 1/100 dBc.
rngAndDopplerExtractionRngToCarrierPowerRatioParamOid	 OBJECT IDENTIFIER ::= { 1 3 112 4 4 2 1 20301 1 10 1 1 }

-- The engineering unit of this parameter is 1/100 dB
RngAndDopplerExtractionRngToCarrierPowerRatio	 ::= INTEGER  (-20000 .. 0)


-- This parameter configures and reports in 1/100 radians the expected ranging modulation
--  index on the received carrier.
rngAndDopplerExtractionExpectedRngModIndexParamOid	 OBJECT IDENTIFIER ::= { 1 3 112 4 4 2 1 20301 1 11 1 1 }

-- The engineering unit of this parameter is 1/100 radian.
RngAndDopplerExtractionExpectedRngModIndex	 ::= INTEGER  (0 .. 140)


-- This parameter configures and reports the tone integration time in milliseconds.
rngAndDopplerExtractionToneIntegrationTimeParamOid	 OBJECT IDENTIFIER ::= { 1 3 112 4 4 2 1 20301 1 12 1 1 }

-- The engineering unit of this parameter is 1/1000 second.
RngAndDopplerExtractionToneIntegrationTime	 ::= INTEGER  (1 .. 100000)


-- This parameter configures and reports the integration time in seconds for the PN
--  code correlator. This time has to be selected based on the known link budget and
--  dynamics.
rngAndDopplerExtractionPnCodeIntegrationTimeParamOid	 OBJECT IDENTIFIER ::= { 1 3 112 4 4 2 1 20301 1 13 1 1 }

-- The engineering unit of this parameter is second.
RngAndDopplerExtractionPnCodeIntegrationTime	 ::= INTEGER  (1 .. 3600)


-- This parameter reports up to which code number the replica has been correlated with
--  the received signal.
rngAndDopplerExtractionCodeNumberCorrelatedParamOid	 OBJECT IDENTIFIER ::= { 1 3 112 4 4 2 1 20301 1 14 1 1 }

RngAndDopplerExtractionCodeNumberCorrelated	 ::= INTEGER  (0 .. 24)


-- This enumerated parameter reports in case of tone/code ranging if the ambiguity has
--  been resolved and in case of PN ranging if lock on the PN sequence has been achieved.
--  It can take on two values:
-- - 'yes': the ranging system has reached the state where
--  range measurements can be performed;
-- - 'no': correlation of the replica of the
--  sent signal with the received signal has not yet been achieved or has failed.
rngAndDopplerExtractionAmbiguityResolvedParamOid	 OBJECT IDENTIFIER ::= { 1 3 112 4 4 2 1 20301 1 15 1 1 }

RngAndDopplerExtractionAmbiguityResolved	 ::= ENUMERATED
{
	 no                  	 	 (0)
,	 yes                 	 	 (1)
}



-- This enumerated parameter configures and reports for Doppler and PN ranging the mode
--  in which the spacecraft transponder is supposed to operate. 
rngAndDopplerExtractionSpacecraftTransponderModeParamOid	 OBJECT IDENTIFIER ::= { 1 3 112 4 4 2 1 20301 1 16 1 1 }

RngAndDopplerExtractionSpacecraftTransponderMode	 ::= SEQUENCE
{
	 doppler             	 ENUMERATED
	 {
	 	 nonCoherent         	 	 (0)
	 ,	 coherent            	 	 (1)
	 }

,	 ranging             	 ENUMERATED
	 {
	 	 passthrough         	 	 (0)
	 ,	 regenerative        	 	 (1)
	 }

}



-- This parameter configures and reports the expected duration of the PN code acquisition
--  by the spacecraft.
rngAndDopplerExtractionExpectedSpacecraftPnAcqDurationParamOid	 OBJECT IDENTIFIER ::= { 1 3 112 4 4 2 1 20301 1 17 1 1 }

-- The engineering unit of this parameter is second.
RngAndDopplerExtractionExpectedSpacecraftPnAcqDuration	 ::= INTEGER  (1 .. 1000)


-- This parameter configures and reports the ranging measurement sampling rate in 1/1000
--  seconds.
rngAndDopplerExtractionRngMeasurementSamplingRateParamOid	 OBJECT IDENTIFIER ::= { 1 3 112 4 4 2 1 20301 1 18 1 1 }

-- The engineering unit of this parameter is 1/1000 second
RngAndDopplerExtractionRngMeasurementSamplingRate	 ::= INTEGER  (1 .. 3600000)


-- This parameter configures and reports the Doppler measurement sampling rate in 1/1000
--  seconds.
rngAndDopplerExtractionDopplerMeasurementSamplingRateParamOid	 OBJECT IDENTIFIER ::= { 1 3 112 4 4 2 1 20301 1 19 1 1 }

-- The engineering unit of this parameter is 1/1000 second
RngAndDopplerExtractionDopplerMeasurementSamplingRate	 ::= INTEGER  (1 .. 3600000)


-- This parameter configures and reports the status of the collection and delivery of
--  radiometric observables. It can take on two values:
-- - 'notActive';
-- - 'auto';
-- -
--  'active'.
-- 
-- Setting this parameter to 'notActive' disables or terminates the collection
--  of radiometric data.
-- When this parameter is 'auto', the time during which the data
--  collection is performed in accordance with the period during which the parameter
--  rngXmitMod of the RngXmit FR is set to 'enabled' shifted by the two-way light time.
--  When the rngXmitMod parameter indicates that ranging calibration is performed, the
--  two-way-light time is disregarded and the delivered range measurements are annotated
--  as calibration data.
-- When the parameter rngAndDopplerExtractionDataCollection is
--  set to 'active', the collection of radiometric observables is attempted regardless
--  of the state of the RngXmit FR. 
-- 
rngAndDopplerExtractionDataCollectionParamOid	 OBJECT IDENTIFIER ::= { 1 3 112 4 4 2 1 20301 1 20 1 1 }

RngAndDopplerExtractionDataCollection	 ::= ENUMERATED
{
	 notActive           	 	 (0)
,	 auto                	 	 (1)
,	 active              	 	 (2)
}



-- This parameter reports the latest Doppler and range measurement and the associated
--  residual, i.e., the measured value minus the predicted value and for range measurements
--  also the differenced range versus integrated Doppler (DRVID) measurement (latest
--  range value minus previously measured range value minus the integrated Doppler for
--  the period between the times when the latest range measurement and the previous
--  range measurement has been taken. 
-- 
-- It should be noted that the reported range
--  measurement value is neither corrected for station and spacecraft delays nor for
--  tropospheric effects. The residual therefore is not correct in absolute terms, but
--  it should be small and stable and therefore is a good indication of the quality
--  of the range measurements. 
-- 
-- DRIVD can only be provided if range and Doppler measuremnts
--  are taken at the same times.
rngAndDopplerExtractionObservableAndResidualParamOid	 OBJECT IDENTIFIER ::= { 1 3 112 4 4 2 1 20301 1 21 1 1 }

RngAndDopplerExtractionObservableAndResidual	 ::= SEQUENCE
{
	 doppler             	 SEQUENCE
	 {

	 	 -- The engineering unit of this element is Hz.
	 	 dopplerShift        	 INTEGER  (-1000000 .. 1000000)
,
	 	 -- The engineering unit of this element is Hz.
	 	 dopplerShiftResidual	 INTEGER  (-100000 .. 100000)
	 }

,	 range               	 SEQUENCE
	 {

	 	 -- The engineering unit of this parameter is km
	 	 rangeValue          	 INTEGER  (0 .. 5000000000)
,
	 	 -- The engineering unit of this element is 1/100 m.
	 	 rangeValueResidual  	 INTEGER  (-100000000 .. 100000000)
,
	 	 -- Differenced Range versus Integrated Doppler (DRVID) measurement in 1/100 m.
	 	 drvid               	 INTEGER  (-100000000 .. 100000000)
	 }

}



-- This parameter reports the number of Doppler and range observables generated since
--  the most recent start of the collection of observables by setting the parameter
--  rngAndDopplerExtractionDataCollection to 'active'.
rngAndDopplerExtractionObservablesCountParamOid	 OBJECT IDENTIFIER ::= { 1 3 112 4 4 2 1 20301 1 22 1 1 }

RngAndDopplerExtractionObservablesCount	 ::= SEQUENCE
{
	 dopplerObservablesCount	 INTEGER  (0 .. 4294967295)
,	 rangeObservablesCount	 INTEGER  (0 .. 4294967295)
}



-- This event notifies any change of the rngAndDopplerExtractionResourceStat parameter
--  value.
rngAndDopplerExtractionResourceStatChangeEventOid	 OBJECT IDENTIFIER ::= { 1 3 112 4 4 2 1 20301 2 1 1 }




-- The event value reports the rngAndDopplerExtractionResourceStat value that applies
--  since the notified rngAndDopplerExtractionResourceStatChange event has occurred.
rngAndDopplerExtractionResourceStatChangeEventValueValueOid	 OBJECT IDENTIFIER ::= { 1 3 112 4 4 2 1 20301 2 1 1 1 }

RngAndDopplerExtractionResourceStatChangeEventValue	 ::= RngAndDopplerExtractionResourceStat


-- By means of this event any change in the capability to deliver radiometric observables
--  is notified. This is reported both for Doppler and for range measurements. The reporting
--  for range measurements refers to the ranging mode selected by the rngXmitRngType
--  parameter of the RngXmit FR.
rngAndDopplerExtractionStatChangeEventOid	 OBJECT IDENTIFIER ::= { 1 3 112 4 4 2 1 20301 2 2 1 }




-- This parameter reports if radiometric observables can be delivered. Data collection
--  may not be possible because e.g. the receiver is not locked on the carrier or for
--  range measurements the ambiguity resolution has failed.
rngAndDopplerExtractionStatChangeEventValueValueOid	 OBJECT IDENTIFIER ::= { 1 3 112 4 4 2 1 20301 2 2 1 1 }

RngAndDopplerExtractionStatChangeEventValue	 ::= SEQUENCE
{
	 dopplerDataCollection	 ENUMERATED
	 {
	 	 notOkay             	 	 (0)
	 ,	 okay                	 	 (1)
	 }

,	 rngDataCollection   	 ENUMERATED
	 {
	 	 notOkay             	 	 (0)
	 ,	 okay                	 	 (1)
	 }

}



-- This directive permits setting of the controllable parameters of the RngAndDopplerExtraction
--  FR type. 
rngAndDopplerExtractionSetContrParamsDirectiveOid	 OBJECT IDENTIFIER ::= { 1 3 112 4 4 2 1 20301 3 1 1 }




-- The directive qualifier specifies the FR instance the directive shall act on and
--  contains a set of parameter identifier and parameter value pairs. To be valid, the
--  parameter identifier must reference a controllable parameter of the RngAndDopplerExtraction
--  FR and the parameter value must be of the same type as the parameter value that
--  shall be set.
rngAndDopplerExtractionContrParamIdsAndValuesQualifierOid	 OBJECT IDENTIFIER ::= { 1 3 112 4 4 2 1 20301 3 1 1 1 }

RngAndDopplerExtractionContrParamIdsAndValues	 ::= DirectiveQualifier


-- The TcPlopSyncAndChannelEncoding FR accepts as input one of the following:
-- - CLTUs;
-- -
--  TC frames to be radiated via a specific physical channel.
-- It also accepts the CLCWs
--  extracted from the telemetry link associated with the telecommand link used by this
--  FR.
-- This FR provides the symbol stream to be used for modulating the transmitted
--  carrier of the physical channel associated with this FR. 
tcPlopSyncAndChnlEncodeFrOid	 OBJECT IDENTIFIER ::= { 1 3 112 4 4 2 1 30100 }




-- This enumerated parameter reports the TcPlopSyncAndChnlEncode FR resource status
--  and can take on four values:
-- - 'configured'; 
-- - 'operational';
-- - 'interrupted';
-- -
--  'halted'.
tcPlopSyncResourceStatParamOid	 OBJECT IDENTIFIER ::= { 1 3 112 4 4 2 1 30100 1 1 1 1 }

TcPlopSyncResourceStat	 ::= ResourceStat


-- This parameter configures and reports the maximum length in octets of a CLTU the
--  FR will forward to the Ccsds401SpaceLinkCarrierXmit FR. If the given FR instance
--  is not configured to accept CLTUs as incoming service data units, the value of this
--  parameter shall be flagged as 'undefined'.
tcPlopSyncMaxCltuLengthParamOid	 OBJECT IDENTIFIER ::= { 1 3 112 4 4 2 1 30100 1 2 1 1 }

-- The engineering unit of this parameter is octet.
TcPlopSyncMaxCltuLength	 ::= INTEGER  (12 .. 4096)


-- This parameter configures and reports the maximum number of TC MC frames that may
--  be converted into a single CLTU. The value of this parameter must be '1' if  tcPlopSyncMaxCltuRepetitions
--  ≠ 1. If the given FR instance is not configured to accept TC MC frames as incoming
--  service data unit, the value of this parameter shall be flagged as 'undefined'.
tcPlopSyncMaxNumberOfFramesPerCltuParamOid	 OBJECT IDENTIFIER ::= { 1 3 112 4 4 2 1 30100 1 3 1 1 }

TcPlopSyncMaxNumberOfFramesPerCltu	 ::= INTEGER  (1 .. 15)


-- This parameter configures and reports the encoding and randomization applied to the
--  TC frames. 
tcPlopSyncEncodeTypeParamOid	 OBJECT IDENTIFIER ::= { 1 3 112 4 4 2 1 30100 1 4 1 1 }

TcPlopSyncEncodeType	 ::= CHOICE
{
	 noEncoding          	 [0]	 	 Randomization (off)
,	 bchEncoding         	 [1]	 	 Randomization
,	 ldpcEncoding        	 [2]	 	 SEQUENCE
	 {
	 	 randomization       	 Randomization (on)
,	 	 ldpcCoding          	 CHOICE
	 	 {
	 	 	 code1               	 [0]	 	 SEQUENCE
	 	 	 {
	 	 	 	 n                   	 INTEGER  (128)
,	 	 	 	 k                   	 INTEGER  (64)
,	 	 	 	 tailSequence        	 ENUMERATED
	 	 	 	 {
	 	 	 	 	 used                	 	 (0)
	 	 	 	 ,	 notUsed             	 	 (1)
	 	 	 	 }

	 	 	 }

,	 	 	 code2               	 [1]	 	 SEQUENCE
	 	 	 {
	 	 	 	 n                   	 INTEGER  (512)
,	 	 	 	 k                   	 INTEGER  (256)
	 	 	 }

	 	 }

	 }

}



-- This parameter configures and reports how many times a given CLTU may at most be
--  repeated on the telecommand link. The value of this parameter must be '1' if tcPlopSyncMaxNumberOfFramesPerCltu
--  ≠ 1. If the given instance of the FR is not configured to accept MC TC frames as
--  incoming service data unit, the value of this parameter shall be flagged as 'undefined'.
-- Note:
--  If tcPlopSyncAndChnlEncodingMaxCltuRepetitions = 1, the repeated transmissions option
--  is either disabled or not supported.
tcPlopSyncMaxCltuRepetitionsParamOid	 OBJECT IDENTIFIER ::= { 1 3 112 4 4 2 1 30100 1 5 1 1 }

TcPlopSyncMaxCltuRepetitions	 ::= INTEGER  (1 .. 5)


-- This enumerated parameter configures and reports the Physical Layer Operation Procedure
--  that the TcPlopSyncAndChannelEncode FR applies (PLOP1 or PLOP2). If PLOP1 applies,
--  the parameter also specifies the length of the idle sequence (in octets).
-- 
-- 
-- The
--  exact behavior of the FR as determined by the selected PLOP in effect is further
--  described in the F-CLTU specification CCSDS 912.1-B-3.
-- 
-- 
tcPlopSyncPlopParamOid	 OBJECT IDENTIFIER ::= { 1 3 112 4 4 2 1 30100 1 6 1 1 }

TcPlopSyncPlop      	 ::= CHOICE
{

	 -- The engineering unit of this element is cotet.
	 plop1IdleSequenceLength	 [0]	 	 INTEGER  (0 .. 255)
,	 plop2               	 [1]	 	 NULL
}



-- This parameter configures and reports the size, in octets, and pattern of the bit
--  pattern to be radiated to enable the spacecraft telecommand system to achieve bit
--  lock (acquisition sequence) and to the bit pattern to maintain bit lock while no
--  command is being radiated (idle pattern). The radiation of the acquisition and idle
--  sequence will be performed in accordance with the applicable Physical Layer Operations
--  Procedure (PLOP) - cf. tcPlopSyncPlop.
tcPlopSyncAcqAndIdlePatternParamOid	 OBJECT IDENTIFIER ::= { 1 3 112 4 4 2 1 30100 1 7 1 1 }

-- The engineering unit of this parameter is octet.
TcPlopSyncAcqAndIdlePattern	 ::= SEQUENCE
{
	 acquisitionSequence 	 SEQUENCE
	 {
	 	 acquisitionPattern  	 CHOICE
	 	 {

	 	 	 -- The pattern specified in CCSDS 232.0-B-3 starting with 0.
	 	 	 ccsds0              	 [0]	 	 OCTET STRING ('55'H) (SIZE( 1)) 
,
	 	 	 -- The pattern specified in CCSDS 232.0-B-3 starting with 1.
	 	 	 ccsds1              	 [1]	 	 OCTET STRING ('AA'H) (SIZE( 1)) 
,	 	 	 nonCcsds            	 [2]	 	 OCTET STRING (SIZE( 1)) 
	 	 }

,
	 	 -- The engineering unit of this element is octet
	 	 acquisitionSequenceLength	 INTEGER  (1 .. 256)
	 }

,	 idlePattern         	 CHOICE
	 {

	 	 -- The pattern specified in CCSDS 232.0-B-3 starting with 0.
	 	 ccsds0              	 [0]	 	 OCTET STRING ('55'H) (SIZE( 1)) 
,
	 	 -- The pattern specified in CCSDS 232.0-B-3 starting with 1.
	 	 ccsds1              	 [1]	 	 OCTET STRING ('AA'H) (SIZE( 1)) 
,	 	 nonCcsds            	 [2]	 	 OCTET STRING (SIZE( 1)) 
	 }

}



-- This parameter configures and reports the minimum time that the FR instance will
--  ensure between the completion of the radiation of one CLTU and the beginning of
--  the radiation of the following CLTU. There are two ways in which this guard time
--  can be specified:
-- - absolute time in microseconds (the exact effect of the delay
--  time depending on the PLOP is further described in the F-CLTU specification CCSDS
--  912.1-B-3);
-- - number of times the post-CLTU pattern (if applicable) and the pre-CLTU
--  pattern shall be repeated before the next CLTU may be radiated (it should be noted
--  that in this case the length of the guard time varies with the TC symbol rate).
-- 
tcPlopSyncMinDelayTimeParamOid	 OBJECT IDENTIFIER ::= { 1 3 112 4 4 2 1 30100 1 8 1 1 }

-- The engineering unit of this parameter is 1/1000000 second, i.e. microsecond.
TcPlopSyncMinDelayTime	 ::= CHOICE
{

	 -- The engineering unit of this element is 1/1000000 s (microsecond).
	 absoluteGuardTime   	 [0]	 	 INTEGER  (0 .. 1000000)
,	 postPreCltuPatternRepetition	 [1]	 	 INTEGER  (0 .. 10000)
}



-- This enumerated parameter reports the status of the forward link as it can be derived
--  from the Communication Link Control Word (CLCW) in the associated telemetry stream.
--  It can take on the following values:
-- - 'forward link status not available': no
--  CLCWs from the spacecraft have been received by the service provider;
-- - 'no rf
--  available': the service provider has received at least one CLCW; in the last CLCW
--  received by the service provider, the bit that flags ‘No RF Available’ was set to
--  ‘1’;
-- - 'no bit lock': the service provider has received at least one CLCW; in the
--  last CLCW received by the service provider, the bit that flags ‘No RF Available’
--  was set to ‘0’, and the bit that flags ‘No Bit Lock’ was set to ‘1;
-- - 'nominal':
--  the provider has received at least one CLCW; in the last CLCW received by the provider,
--  the bit that flags ‘No RF Available’ was set to ‘0’, and the bit that flags ‘No
--  Bit Lock’ was set to ‘0’.
tcPlopSyncTcLinkStatParamOid	 OBJECT IDENTIFIER ::= { 1 3 112 4 4 2 1 30100 1 9 1 1 }

TcPlopSyncTcLinkStat	 ::= TcLinkStat


-- This parameter configures and reports the Master or Virtual Channel that carries
--  the CLCW to be used to determine the telecommand link RF and/or bit lock status,
--  if applicable, and if and how the CLCW shall be evaluated for the Carrier Modulation
--  Modes (CMM) transitions of the PLOP. The CLCW source is identified by the concatenation
--  of the CCSDS assigned Spacecraft Identifier (SCID), the Transfer Frame Version Number
--  (TFVN) and, if applicable, the Virtual Channel Identifier (VCID). The range of the
--  Spacecraft Identifier and the Virtual Channel Identifier depends on the TFVN as
--  follows:
-- - TFVN = 0 (version 1) - SCID = (0 .. 1023), VCID = (0 .. 7);
-- - TFVN
--  = 1 (version 2) - SCID = (0 .. 255), VCID = (0 .. 63);
-- -TFVN = 12 (version 4) -
--  SCID = (0 .. 65535), VCID = (0 .. 63).
tcPlopSyncClcwEvaluationParamOid	 OBJECT IDENTIFIER ::= { 1 3 112 4 4 2 1 30100 1 10 1 1 }

TcPlopSyncClcwEvaluation	 ::= CHOICE
{
	 noEvaluation        	 [0]	 	 NULL
,	 evaluation          	 [1]	 	 SEQUENCE
	 {
	 	 linkCondition       	 ENUMERATED
	 	 {
	 	 	 noEvaluation        	 	 (0)
	 	 ,	 rfAvailableVerified 	 	 (1)
	 	 ,	 bitLockVerified     	 	 (2)
	 	 ,	 rfAvailableAndBitLockVerified	 	 (3)
	 	 }

,	 	 clcwSource          	 CHOICE
	 	 {

	 	 	 -- This choice is for CLCW extraction from telemetry (TM) frames.
	 	 	 tfvn0               	 [0]	 	 SEQUENCE
	 	 	 {
	 	 	 	 tfvn                	 INTEGER  (0)
,	 	 	 	 scid                	 INTEGER  (0 .. 1023)
,	 	 	 	 vcid                	 CHOICE
	 	 	 	 {
	 	 	 	 	 masterChannel       	 [0]	 	 NULL
,	 	 	 	 	 virtualChannel      	 [1]	 	 INTEGER  (0 .. 7)
	 	 	 	 }

	 	 	 }

,
	 	 	 -- This choice is for CLCW extraction from AOS frames.
	 	 	 tfvn1               	 [1]	 	 SEQUENCE
	 	 	 {
	 	 	 	 tfvn                	 INTEGER  (1)
,	 	 	 	 scid                	 INTEGER  (0 .. 255)
,	 	 	 	 vcid                	 CHOICE
	 	 	 	 {
	 	 	 	 	 masterChannel       	 [0]	 	 NULL
,	 	 	 	 	 virtualChannel      	 [1]	 	 INTEGER  (0 .. 63)
	 	 	 	 }

	 	 	 }

,
	 	 	 -- This choice is for CLCW extraction from USLP frames.
	 	 	 tfvn4               	 [2]	 	 SEQUENCE
	 	 	 {
	 	 	 	 tfvn                	 INTEGER  (12)
,	 	 	 	 scid                	 INTEGER  (0 .. 65535)
,	 	 	 	 vcid                	 CHOICE
	 	 	 	 {
	 	 	 	 	 masterChannel       	 [0]	 	 NULL
,	 	 	 	 	 virtualChannel      	 [1]	 	 INTEGER  (0 .. 63)
	 	 	 	 }

	 	 	 }

	 	 }

	 }

}



-- This event notifies any change of the tcPlopSyncResourceStat parameter.
tcPlopSyncResourceStatChangeEventOid	 OBJECT IDENTIFIER ::= { 1 3 112 4 4 2 1 30100 2 1 1 }




-- The event value reports the tcPlopSyncResourceStat value that applies since the notified
--  tcPlopSyncResourceStatChange event occurred.
tcPlopSyncResourceStatChangeEventValueValueOid	 OBJECT IDENTIFIER ::= { 1 3 112 4 4 2 1 30100 2 1 1 1 }

TcPlopSyncResourceStatChangeEventValue	 ::= TcPlopSyncResourceStat


-- This event notifies any change of the tcPlopSyncTcLinkStat parameter.
tcPlopSyncTcLinkStatChangeEventOid	 OBJECT IDENTIFIER ::= { 1 3 112 4 4 2 1 30100 2 2 1 }




-- The event value reports the tcPlopSyncTcLinkStat value that applies since the notified
--  tcPlopSyncTcLinkStatChange event occurred.
tcPlopSyncTcLinkStatChangeEventValueValueOid	 OBJECT IDENTIFIER ::= { 1 3 112 4 4 2 1 30100 2 2 1 1 }

TcPlopSyncTcLinkStatChangeEventValue	 ::= TcPlopSyncTcLinkStat


-- This event notifies when processing of the given data unit is completed. The data
--  unit is identified by its data-unit-id and the service-instance-id of the service
--  that submitted the data unit for processing.
tcPlopSyncDataUnitProcessingCompletedEventOid	 OBJECT IDENTIFIER ::= { 1 3 112 4 4 2 1 30100 2 3 1 }




-- The event value identifies the data unit that completed processing by reporting the
--  data-unit-id of the data unit and the id of the service instance that submitted
--  the data unit for processing. Note that the data unit may either be a frame or a
--  CLTU.
tcPlopSyncDataUnitProcessingCompletedEventValueValueOid	 OBJECT IDENTIFIER ::= { 1 3 112 4 4 2 1 30100 2 3 1 1 }

TcPlopSyncDataUnitProcessingCompletedEventValue	 ::= SEQUENCE
{
	 dataUnitId          	 INTEGER  (0 .. 4294967295)
,	 serviceInstanceIdentifier	 CHOICE
	 {
	 	 sleServiceInstance  	 [0]	 	 SleSvcInstanceId
,	 	 cstsServiceInstance 	 [1]	 	 CstsSvcInstanceId
	 }

}



-- This directive permits setting of the controllable parameters of the TcPlopSyncAndChnlEncode
--  FR type. 
tcPlopSyncSetContrParamsDirectiveOid	 OBJECT IDENTIFIER ::= { 1 3 112 4 4 2 1 30100 3 1 1 }




-- The directive qualifier specifies the FR instance the directive shall act on and
--  contains a set of parameter identifier and parameter value pairs. To be valid, the
--  parameter identifier must reference a controllable parameter of the TcPlopSyncAndChnlEncode
--  FR and the parameter value must be of the same type as the parameter value that
--  shall be set.
-- 
tcPlopSyncContrParamIdsAndValuesQualifierOid	 OBJECT IDENTIFIER ::= { 1 3 112 4 4 2 1 30100 3 1 1 1 }

TcPlopSyncContrParamIdsAndValues	 ::= DirectiveQualifier


-- When the FR receives this directive, it discards all data units that are associated
--  with the service-instance-id specified in the directive qualifier.
tcPlopSyncDiscardDataUnitsDirectiveOid	 OBJECT IDENTIFIER ::= { 1 3 112 4 4 2 1 30100 3 2 1 }




-- The qualifier specifies the service-instance-id with which the data units to be discarded
--  are associated.
tcPlopSyncFrAndServiceInstanceIdQualifierOid	 OBJECT IDENTIFIER ::= { 1 3 112 4 4 2 1 30100 3 2 1 1 }

TcPlopSyncFrAndServiceInstanceId	 ::= SEQUENCE
{
	 functResourceInstanceNumber	 INTEGER  (1 .. 4294967295)
,	 serviceInstanceId   	 CHOICE
	 {
	 	 sleServiceInstanceId	 [0]	 	 SleSvcInstanceId
,	 	 cstsServiceInstanceId	 [1]	 	 CstsSvcInstanceId
	 }

}



-- This FR can be configured to accept one of the following input types:
-- - CADUs to
--  be radiated via a specific physical channel;
-- - fixed-length frames (including,
--  but not necessarily limited to, AOS and USLP) to be radated via a specific physical
--  channel. 
-- This FR provides the symbol stream to be used for modulating the forward
--  carrier of the physical channel associated with this FR. 
flfSyncChnlEncodeAndOidGenFrOid	 OBJECT IDENTIFIER ::= { 1 3 112 4 4 2 1 30200 }




-- This enumerated parameter reports the FlfSyncChnlEncodeAndOidGen FR resource status
--  and can take on four values:
-- -  - 'configured': the associated equipment has been
--  configured
--     - 'operational': the associated equipment is active;
--     - 'interrupted':
--  a failure has been detected;
--     - 'halted': the associated equipment has been
--  taken out of service.
-- 
flfSyncEncResourceStatParamOid	 OBJECT IDENTIFIER ::= { 1 3 112 4 4 2 1 30200 1 1 1 1 }

FlfSyncEncResourceStat	 ::= ResourceStat


-- This parameter configures and reports the length in octets of the fixed-length SL-PDUs
--   (transfer frames or CADUs) that are input to the FR. 
flfSyncEncSlpduLengthParamOid	 OBJECT IDENTIFIER ::= { 1 3 112 4 4 2 1 30200 1 2 1 1 }

FlfSyncEncSlpduLength	 ::= INTEGER  (6 .. 4294967295)


-- This parameter configures and reports the selected coding scheme and related configuration
--  parameter values. The ASM is attached for all choices except 'cadu', where it is
--  disallowed.
flfSyncEncCodingSelectionParamOid	 OBJECT IDENTIFIER ::= { 1 3 112 4 4 2 1 30200 1 3 1 1 }

FlfSyncEncCodingSelection	 ::= CHOICE
{

	 -- optional randomization, ASM attachment, optional convolutional encoding only
	 encodingBypass      	 [0]	 	 SEQUENCE
	 {
	 	 randomization       	 Randomization
,	 	 covolutionalEncoding	 ConvolutionalEncoding
	 }

,	 reedSolomon         	 [1]	 	 SEQUENCE
	 {
	 	 randomization       	 Randomization
,	 	 convolutionalEncoding	 ConvolutionalEncoding
,	 	 errorCorrectionCapability	 ENUMERATED
	 	 {
	 	 	 eight               	 	 (0)
	 	 ,	 sixteen             	 	 (1)
	 	 }

,	 	 interleavingDepth   	 RsInterleavingDepth
	 }

,
	 -- ASM is applied, convolutional encoding is disallowed for the LDPC Frame coding choice.
	 ldpcFrame           	 [2]	 	 SEQUENCE
	 {
	 	 randomization       	 Randomization
,	 	 ldpcCodeRateAndInfoBlockLength	 LdpcCodeRateAndInfoBlockLength
	 }

,
	 -- randomization is required and convolutional coding is disabled for LDPC slicing
	 ldpcSlice           	 [3]	 	 SEQUENCE
	 {
	 	 ldpcCodeRateAndInfoBlockLength	 LdpcCodeRateAndInfoBlockLength
,	 	 ldpcCodeblockSize   	 INTEGER  (1 .. 8)
	 }

,
	 -- Only optional convolutional encoding is available for the CADU option
	 cadu                	 [4]	 	 ConvolutionalEncoding
}



-- This event notifies any change of the flfSyncEncResourceStat parameter.
flfSyncEncResourceStatChangeEventOid	 OBJECT IDENTIFIER ::= { 1 3 112 4 4 2 1 30200 2 1 1 }




-- The event value reports the fwdFlfSyncResourceStat value that applies since the notified
--  fwdFlfEncResourceStatChange event occurred.
flfSyncEncResourceStatValueValueOid	 OBJECT IDENTIFIER ::= { 1 3 112 4 4 2 1 30200 2 1 1 1 }

FlfSyncEncResourceStatValue	 ::= FlfSyncEncResourceStat


-- This event notifies the completion of processing of a data unit. This event is emitted
--  only for data units that are transferred through an instance of a Cross Support
--  Transfer Service (CSTS) that uses the CSTS Specification Framework Data Processing
--  procedure  or a procedure derived from it. Each data unit received from such a CSTS
--  is annotated with the service-instance-id  of the source CSTS instance and the data-unit-id
--  of the PROCESS-DATA invocation that carries that data unit.
flfSyncEncDataUnitProcessingCompletedEventOid	 OBJECT IDENTIFIER ::= { 1 3 112 4 4 2 1 30200 2 2 1 }




-- This parameter contains the data-unit-id of the data unit that has completed processing,
--  and the service-instance -identifier of the CSTS instance through which the data
--  unit was received.
flfSyncEncDataUnitProcessingCompletedValueValueOid	 OBJECT IDENTIFIER ::= { 1 3 112 4 4 2 1 30200 2 2 1 1 }

FlfSyncEncDataUnitProcessingCompletedValue	 ::= DataUnitProcessingCompletedEventValue


-- This directive permits setting of the controllable parameters of the flfSyncChnlEncodeAndOidGen
--  FR type.  
flfSyncEncSetContrParamsDirectiveOid	 OBJECT IDENTIFIER ::= { 1 3 112 4 4 2 1 30200 3 1 1 }




-- The directive qualifier specifies the FR instance the directive shall act on and
--  contains a set of parameter identifier and parameter value pairs. To be valid, the
--  parameter identifier must reference a controllable parameter of the flfSyncChannelEncodingAndOidGen
--  FR and the parameter value must be of the same type as the parameter value that
--  shall be set.
-- 
flfSyncEncContrParamIdsAndValuesQualifierOid	 OBJECT IDENTIFIER ::= { 1 3 112 4 4 2 1 30200 3 1 1 1 }

FlfSyncEncContrParamIdsAndValues	 ::= DirectiveQualifier


-- Upon receipt of this directive, the FlfSyncChnlEncodeAndOidGen FR discards all data
--  units that are accompanied by the service-instance-id that is identified in the
--  directive qualifier.
-- 
-- The qualifier of this directive event is the service-instance-id
--  of the CSTS for which the data units are to discarded
-- 
-- This directive is applicable
--  only for data units that annotated with the service-instance-id of the CSTS instance
--  that provided those data units.
-- 
flfSyncEncDiscardDataUnitsDirectiveOid	 OBJECT IDENTIFIER ::= { 1 3 112 4 4 2 1 30200 3 2 1 }




-- The service-instance-id of the CSTS for which the data units are to discarded when
--  the fflfSyncDiscardDataUnits directive is invoked.
flfSyncEncDiscardDataUnitsSvcInstanceIdQualifierOid	 OBJECT IDENTIFIER ::= { 1 3 112 4 4 2 1 30200 3 2 1 1 }

FlfSyncEncDiscardDataUnitsSvcInstanceId	 ::= CstsSvcInstanceId


-- The FlfSyncAndChnlDecode FR accepts as input the symbol stream from the Ccsds401SpaceLinkCarrierRcpt
--  FR. It provides the decoded and annotated telemetry frames to the RafTsProvider,
--  the RcfTsProvider, the RocfTsProvider, to the McDemuxReception and to the TmFrameDataSink
--  FRs.
flfSyncAndChnlDecodeFrOid	 OBJECT IDENTIFIER ::= { 1 3 112 4 4 2 1 30300 }




-- This enumerated parameter reports the fixed length frame synchronization and decoding
--  resource status and can take on four values:
-- - 'configured': the synchronization
--  and decoding equipment has been configured, but no incoming symbol stream is present;
-- -
--  'operational': the telemetry reception is active, i.e., all syncronization and decoding
--  is in nominal condition;
-- - 'interrupted': a failure has been detected, e.g. the
--  incoming data cannot be decoded;
-- - 'halted': the telemetry reception has been taken
--  out of service. 
flfSyncDecResourceStatParamOid	 OBJECT IDENTIFIER ::= { 1 3 112 4 4 2 1 30300 1 1 1 1 }

FlfSyncDecResourceStat	 ::= ResourceStat


-- This parameter configures and reports the ASM pattern and the frame synchronizer
--  behavior in terms of the correlation error threshold for declaring 'ASM lock', and
--  for declaring 'ASM out of lock', the number of consecutive frames with 'ASM lock'
--  required to transition from 'notLocked' to 'verify', the number of consecutive frames
--  with 'ASM lock' required to transition from 'verify' to 'locked' and the number
--  of consecutive frames with 'ASM out of lock' required to transition from 'locked'
--  to 'notLocked' and the to be tolerated ASM position error in number of symbols (i.e.
--  unexpected frame length) for not triggering the transition to 'notLocked'. 
flfSyncDecAsmConfigParamOid	 OBJECT IDENTIFIER ::= { 1 3 112 4 4 2 1 30300 1 2 1 1 }

FlfSyncDecAsmConfig 	 ::= SEQUENCE
{
	 asmPattern          	 CHOICE
	 {
	 	 ccsdsPattern        	 [0]	 	 NULL
,
	 	 -- The length of the ASM pattern is indirectly specified by the length of the octet
	 	 --  string.
	 	 nonCcsdsPattern     	 [1]	 	 OCTET STRING
	 }

,	 asmThresholds       	 SEQUENCE
	 {
	 	 asmCorrelationLockThreshold	 INTEGER  (0 .. 191)
,	 	 asmCorrelationOutOfLockThreshold	 INTEGER  (1 .. 192)
,	 	 verifyThreshold     	 INTEGER  (1 .. 15)
,	 	 lockedThreshold     	 INTEGER  (1 .. 15)
,	 	 notLockedThreshold  	 INTEGER  (1 .. 15)
,
	 	 -- in number of symbols
	 	 frameLengthErrorThreshold	 INTEGER  (-10 .. 10)
	 }

}



-- This parameter reports the number of symbols in the most recently received ASM that
--  differ from the nominal ASM pattern. When comparing these numbers, one needs to
--  take into consideration whether the synchronization is done on the (pre Viterbi
--  decoder) symbol stream or on the (post Viterbi decoder) bit stream which may be
--  the case if flfSyncDecode is either 'convolutional' or 'concatenated'.
-- The frame
--  synchronization is also used to remove the phase ambiguity of some modulation schemes.
--  To that end, the correlation process is performed both for the standard ASM pattern
--  and its inversion.
-- A given implementation will specify if the the synchronization
--  is performed in the symbol or bit domain. This shall be recorded in the Service
--  Agreement.
flfSyncDecAsmCorrelationErrorParamOid	 OBJECT IDENTIFIER ::= { 1 3 112 4 4 2 1 30300 1 3 1 1 }

FlfSyncDecAsmCorrelationError	 ::= INTEGER  (0 .. 192)


-- This enumerated parameter reports the frame synchronizer lock status. It can take
--  on the following values:
-- - 'locked': The synchronizer has found at least two Attached
--  Sync Markers with the expected number of symbols or bits between them and with each
--  ASM having a correlation error that is lower than the configured error limit;
-- -
--  'verify': the frame synchronizer has found one ASM in the symbol or bit stream with
--  the correlation error lower than the configured threshold and is looking for a second
--  ASM at the expected number of symbols or bits after the first ASM; if such ASM is
--  found, the lock status changes to 'locked'; if no ASM is found where expected, the
--  lock status changes to 'not locked'; if an ASM is found, but at a larger distance
--  in terms of symbols or bits than expected, that newly found ASM will be the reference
--  for searching the next verification ASM;
-- - not locked: the frame synchronizer did
--  not find any ASM with a correlation error below the correlation error limit. 
flfSyncDecFrameSyncLockStatParamOid	 OBJECT IDENTIFIER ::= { 1 3 112 4 4 2 1 30300 1 4 1 1 }

FlfSyncDecFrameSyncLockStat	 ::= ENUMERATED
{
	 notLocked           	 	 (0)
,	 locked              	 	 (1)
,	 verify              	 	 (2)
}



-- This enumerated parameter reports if, based on the observed polarity of the ASM,
--  the symbol stream had to be inverted or not. It can take two values:
-- - 'yes': the
--  frame synchronizer locked on the inverted ASM pattern and therefore inverts the
--  polarity of the symbol stream;
-- - 'no': the frame synchronizer locked on the ASM
--  with the pattern in positive logic and therefore does not invert the symbol stream.
-- As
--  long as flfSyncDecFrameSyncLockStat ≠ 'locked', this parameter shall be flagged
--  as unavailable.
flfSyncDecSymbolInversionParamOid	 OBJECT IDENTIFIER ::= { 1 3 112 4 4 2 1 30300 1 5 1 1 }

FlfSyncDecSymbolInversion	 ::= ENUMERATED
{
	 yes                 	 	 (0)
,	 no                  	 	 (1)
}



-- The parameter reports the ratio of erred frames to the total number of frames processed
--  for the most recent n frames. The value of n shall be documented in the Service
--  Agreeemnet. If the frames are RS or LDPC encoded, then frames for which the RS or
--  LDPC correction is not possible are considered erred. Frames are also considered
--  erred if the FECF is present and the check of the FECF is negative. In all other
--  cases, i.e., if the frames are neither RS nor LDPC encoded nor do they contain a
--  CCSDS compliant FECF, this parameter shall be flagged as 'undefined'.
flfSyncDecFrameErrorRateParamOid	 OBJECT IDENTIFIER ::= { 1 3 112 4 4 2 1 30300 1 6 1 1 }

FlfSyncDecFrameErrorRate	 ::= REAL (0 .. 1)


-- This parameter reports the number of bits in the frame corrected by means of the
--  RS trailer. The number of bits that can be corrected depends on the coding and the
--  interleaving depth. If flfSyncDecDecode is neither 'reedSolomon' nor 'concatenated',
--  this parameter shall be flagged as 'undefined'.
flfSyncDecNumberOfRsErrorsCorrectedParamOid	 OBJECT IDENTIFIER ::= { 1 3 112 4 4 2 1 30300 1 7 1 1 }

FlfSyncDecNumberOfRsErrorsCorrected	 ::= INTEGER  (0 .. 128)


-- This enumerated parameter reports if the time tags used to annotate the telemetry
--  frames with the Earth Receive Time (ERT) are generated by a time code generator
--  slaved to a high precision reference or if this generator is free running. It can
--  take on two values:
-- - 'yes' - The time tags are generated by a system that is locked
--  to the station's frequency and timing system;
-- - 'no' - the system generating the
--  time tags is free-running. 
flfSyncDecErtAnnotationLockedToReferenceParamOid	 OBJECT IDENTIFIER ::= { 1 3 112 4 4 2 1 30300 1 8 1 1 }

FlfSyncDecErtAnnotationLockedToReference	 ::= ENUMERATED
{
	 no                  	 	 (0)
,	 yes                 	 	 (1)
}



-- This parameter configures and reports the length in octets of the CADU the frame
--  synchronizer shall attempt to lock on. Depending on the implementation, the frame
--  synchronizer may operate on the convolutionally encoded symbol stream or the already
--  convolutionally decoded symbol stream, if convolutional encoding is applied at all.
flfSyncDecCaduLengthParamOid	 OBJECT IDENTIFIER ::= { 1 3 112 4 4 2 1 30300 1 9 1 1 }

FlfSyncDecCaduLength	 ::= INTEGER  (48 .. 32768)


-- This enumerated parameter configures and reports if the FR is configured to derandomize
--  the incoming frames. This parameter can take on two values:
-- - 'derandomization';
-- -
--  'no derandomization'.
-- The details regarding the randomization are specified in
--  CCSDS 131.0-B-3. Randomization is strongly advised, but mandatory only for punctured
--  convolutional codes and for LDPC encoded slices.  
flfSyncDecDerandomizationParamOid	 OBJECT IDENTIFIER ::= { 1 3 112 4 4 2 1 30300 1 10 1 1 }

FlfSyncDecDerandomization	 ::= ENUMERATED
{
	 noDerandomization   	 	 (0)
,	 derandomization     	 	 (1)
}



-- This parameter configures and reports the decoding the FlfSyncAndDecode FR is configured
--  to apply to the incoming frames. This parameter can take on the following values:
-- -
--  'no decoding';
-- - 'convolutional';
-- - 'reedSolomon';
-- - 'concatenated';
-- - 'turbo';
-- -
--  'ldpc';
-- - 'slicedLdpc'.
-- For the configured decoding option the parameter also
--  specifies the associated configuration details.
-- 
-- Note: The length and pattern
--  of the ASM is implicitly specified by the decoding that is to be applied except
--  if for parameter flfSyncDecAsmConfig the nonCcsds asmPattern choice is selected..
flfSyncDecDecodeParamOid	 OBJECT IDENTIFIER ::= { 1 3 112 4 4 2 1 30300 1 11 1 1 }

FlfSyncDecDecode    	 ::= SEQUENCE
{

	 -- If applicable, the CCSDS recommendation is NRZ-M.
	 differentialDecode  	 ENUMERATED
	 {
	 	 notApplicable       	 	 (0)
	 ,	 inputIsNrzM         	 	 (1)
	 ,	 inputIsNrzS         	 	 (2)
	 }

,	 symbolDecode        	 CHOICE
	 {
	 	 noDecoding          	 [0]	 	 NULL
,	 	 convolutional       	 [1]	 	 ConvolutionalCodeRate
,	 	 reedSolomon         	 [2]	 	 SEQUENCE
	 	 {
	 	 	 rsCorrectionCapabilty	 ENUMERATED
	 	 	 {
	 	 	 	 corrects8           	 	 (0)
	 	 	 ,	 corrects16          	 	 (1)
	 	 	 }

,	 	 	 rsInterleavingDepth 	 RsInterleavingDepth
	 	 }

,	 	 concatenated        	 [3]	 	 SEQUENCE
	 	 {
	 	 	 convolutional       	 SEQUENCE
	 	 	 {
	 	 	 	 generatorPolynomials	 CHOICE
	 	 	 	 {

	 	 	 	 	 -- G1 transmitted first, G2 output is to be inverted, except for punctured codes.
	 	 	 	 	 ccsds               	 [0]	 	 NULL
,
	 	 	 	 	 -- Also for the nonCcsds case the only constraint length supported is 7.
	 	 	 	 	 nonCcsds            	 [1]	 	 SEQUENCE
	 	 	 	 	 {
	 	 	 	 	 	 g1ConnectionVector  	 BIT STRING (SIZE( 7)) 
,	 	 	 	 	 	 g2ConnectionVector  	 BIT STRING (SIZE( 7)) 
,	 	 	 	 	 	 polynomialSequence  	 ENUMERATED
	 	 	 	 	 	 {
	 	 	 	 	 	 	 g2G1                	 	 (0)
	 	 	 	 	 	 ,	 g1G2                	 	 (1)
	 	 	 	 	 	 }

,	 	 	 	 	 	 polynomialInversion 	 ENUMERATED
	 	 	 	 	 	 {
	 	 	 	 	 	 	 noInversion         	 	 (0)
	 	 	 	 	 	 ,	 g2Inversion         	 	 (1)
	 	 	 	 	 	 ,	 g1Inversion         	 	 (2)
	 	 	 	 	 	 }

	 	 	 	 	 }

	 	 	 	 }

,	 	 	 	 codeRate            	 ConvolutionalCodeRate
	 	 	 }

,	 	 	 rsCorrectionCapabilty	 ENUMERATED
	 	 	 {
	 	 	 	 corrects8           	 	 (0)
	 	 	 ,	 corrects16          	 	 (1)
	 	 	 }

,	 	 	 rsInterleavingDepth 	 RsInterleavingDepth
	 	 }

,	 	 turbo               	 [4]	 	 SEQUENCE
	 	 {
	 	 	 maxNumberOfIterations	 INTEGER  (1 .. 20)
,	 	 	 codeRate            	 ENUMERATED
	 	 	 {
	 	 	 	 rate1Over2          	 	 (0)
	 	 	 ,	 rate1Over3          	 	 (1)
	 	 	 ,	 rate1Over4          	 	 (2)
	 	 	 ,	 rate1Over6          	 	 (3)
	 	 	 }

	 	 }

,
	 	 -- The information block length shall be derived from the CADU length (see flfSyncCaduLength)
	 	 ldpc                	 [5]	 	 ENUMERATED
	 	 {
	 	 	 rate1Over2          	 	 (0)
	 	 ,	 rate2Over3          	 	 (1)
	 	 ,	 rate4Over5          	 	 (2)
	 	 ,	 rate223Over255      	 	 (3)
	 	 }

,	 	 slicedLdpc          	 [6]	 	 SEQUENCE
	 	 {

	 	 	 -- Number of LDPC codewords 
	 	 	 codeBlockSize       	 INTEGER  (1 | 2 | 3 | 4 | 5 | 6 | 7 | 8)
,	 	 	 codeRateAndSliceLength	 CHOICE
	 	 	 {
	 	 	 	 codeRate1Over2      	 [0]	 	 SEQUENCE
	 	 	 	 {
	 	 	 	 	 codeRate            	 LdpcCodeRate (rate1Over2)
,	 	 	 	 	 sliceLength         	 INTEGER  (1024 | 4096 | 16384)
,	 	 	 	 	 csmPattern          	 CHOICE
	 	 	 	 	 {
	 	 	 	 	 	 ccsds               	 [0]	 	 OCTET STRING ('034776C7272895B0'H)
,	 	 	 	 	 	 nonCCSDS            	 [1]	 	 OCTET STRING (SIZE( 4 .. 16)) 
	 	 	 	 	 }

	 	 	 	 }

,	 	 	 	 codeRate2Over3      	 [1]	 	 SEQUENCE
	 	 	 	 {
	 	 	 	 	 codeRate            	 LdpcCodeRate (rate2Over3)
,	 	 	 	 	 sliceLength         	 INTEGER  (1024 | 4096 | 16384)
,	 	 	 	 	 csmPattern          	 CHOICE
	 	 	 	 	 {
	 	 	 	 	 	 ccsds               	 [0]	 	 OCTET STRING ('034776C7272895B0'H)
,	 	 	 	 	 	 nonCCSDS            	 [1]	 	 OCTET STRING (SIZE( 4 .. 16)) 
	 	 	 	 	 }

	 	 	 	 }

,	 	 	 	 codeRate4Over5      	 [2]	 	 SEQUENCE
	 	 	 	 {
	 	 	 	 	 codeRate            	 LdpcCodeRate (rate4Over5)
,	 	 	 	 	 sliceLength         	 INTEGER  (1024 | 4096 | 16384)
,	 	 	 	 	 csmPattern          	 CHOICE
	 	 	 	 	 {
	 	 	 	 	 	 ccsds               	 [0]	 	 OCTET STRING ('034776C7272895B0'H)
,	 	 	 	 	 	 nonCCSDS            	 [1]	 	 OCTET STRING (SIZE( 4 .. 16)) 
	 	 	 	 	 }

	 	 	 	 }

,	 	 	 	 codeRate223Over255  	 [3]	 	 SEQUENCE
	 	 	 	 {
	 	 	 	 	 codeRate            	 LdpcCodeRate (rate223Over255)
,	 	 	 	 	 sliceLength         	 INTEGER  (7136)
,	 	 	 	 	 csmPattern          	 CHOICE
	 	 	 	 	 {
	 	 	 	 	 	 ccsds               	 [0]	 	 OCTET STRING ('1ACFFC1D'H)
,	 	 	 	 	 	 nonCCSDS            	 [1]	 	 OCTET STRING (SIZE( 4 .. 16)) 
	 	 	 	 	 }

	 	 	 	 }

	 	 	 }

	 	 }

	 }

}



-- This parameter configures and reports if in the frame to be processed the FECF is
--  present. It can take on two values:
-- - 'yes';
-- - 'no'.
flfSyncDecFecfPresentParamOid	 OBJECT IDENTIFIER ::= { 1 3 112 4 4 2 1 30300 1 12 1 1 }

FlfSyncDecFecfPresent	 ::= ENUMERATED
{
	 no                  	 	 (0)
,	 yes                 	 	 (1)
}



-- This parameter provides decoding type specific quality indications regarding the
--  decoding process and an estimates of the bit error rate (BER).
-- 
-- The provided BER
--  estimates are not precise. The ASM pattern derived estimate does not reflect the
--  coding gain (except that related to convolutional coding). The RS decoding derived
--  BER estimate also disregards the RS coding gain, but also disregards the errors
--  associated with not decodable RS code words. However, the number of not decodable
--  RS codewords are reported by indirectly by the element ratioBadCodeWordsToTotalCountOfCodeWordsInTheSample.
--  The BER estimates are determined for n consecutive frames where the value of n shall
--  be documented in the Serviced Agreement.
flfSyncDecDecodeQualityIndicationsParamOid	 OBJECT IDENTIFIER ::= { 1 3 112 4 4 2 1 30300 1 13 1 1 }

FlfSyncDecDecodeQualityIndications	 ::= SEQUENCE
{

	 -- This count rolls over to zero.
	 countOfFramesProcessed	 INTEGER  (0 .. 4294967295)
,	 berEstimates        	 SEQUENCE
	 {

	 	 -- Ratio of erred ASM bits to total count of ASM bits evaluated in n consecutive frames
	 	 --  where the value of n shall be documented in the Service Agreement.
	 	 asmDerivedBerEstimate	 REAL (0 .. 1)
,
	 	 -- Ratio of sum of corrected bits in the RS code words to total count of bits in the
	 	 --  code words in n consecutive frames where the value of n shall be documented in the
	 	 --  Service Agreement. Not decodable code words shall be disregarded.
	 	 rsDerivedBerEstimate	 REAL (0 .. 7E-2)
	 }

,	 qualityIndications  	 CHOICE
	 {
	 	 noDecoding          	 [0]	 	 CHOICE
	 	 {

	 	 	 -- No quality indication possible.
	 	 	 fecfAbsent          	 [0]	 	 NULL
,
	 	 	 -- Ratio of frames with bad FECF to the total count of frames over the most recent n
	 	 	 --  frames. The value of n shall be documented in the Service Agreement.
	 	 	 fecfPresent         	 [1]	 	 REAL (0 .. 1)
	 	 }

,
	 	 -- The Viterbi decoder does not provide specific quality indications.
	 	 convolutional       	 [1]	 	 NULL
,	 	 reedSolomonOrConcatenated	 [2]	 	 SEQUENCE
	 	 {
	 	 	 rsDecoderLockStatus 	 ENUMERATED
	 	 	 {
	 	 	 	 notLocked           	 	 (0)
	 	 	 ,	 locked              	 	 (1)
	 	 	 }

,
	 	 	 -- This count rolls over to zero.
	 	 	 countOfRsCodeWordsProcessed	 INTEGER  (0 .. 4294967295)
,
	 	 	 -- Ratio valid for the most recent n code words processed. The value of n shall be documented
	 	 	 --  in the Service Agreement.
	 	 	 ratioBadCodeWordsToTotalCountOfCodeWordsInTheSample	 REAL (0 .. 1)
	 	 }

,	 	 turbo               	 [3]	 	 SEQUENCE
	 	 {
	 	 	 turboDecoderLockStatus	 ENUMERATED
	 	 	 {
	 	 	 	 notLocked           	 	 (0)
	 	 	 ,	 locked              	 	 (1)
	 	 	 }

,	 	 	 iterationsCount     	 SEQUENCE
	 	 	 {

	 	 	 	 -- Value for the most recent n frames. The value of n shall be documented in the Service
	 	 	 	 --  Agreement.
	 	 	 	 maxNumberOfIterationsPerFrame	 INTEGER  (1 .. 20)
,
	 	 	 	 -- The average number multiplied with 1000. The average shall be calculated for the
	 	 	 	 --  most recent n frames processed. The value of n shall be documented in the ServiceAgreement.
	 	 	 	 averageNumberOfIterationsPerFrame	 INTEGER  (1000 .. 20000)
	 	 	 }

,
	 	 	 -- Ratio valid for the most recent n frames processed. The value of n shall be documented
	 	 	 --  in the Service Agreement.
	 	 	 ratioBadFramesToTotalCountOfFramesInTheSample	 REAL (0 .. 1)
	 	 }

,	 	 ldpc                	 [4]	 	 SEQUENCE
	 	 {
	 	 	 ldpcDecoderLockStatus	 ENUMERATED
	 	 	 {
	 	 	 	 notLocked           	 	 (0)
	 	 	 ,	 locked              	 	 (1)
	 	 	 }

,	 	 	 iterationsCount     	 SEQUENCE
	 	 	 {

	 	 	 	 -- Value for the most recent n frames. The value of n shall be documented in the Service
	 	 	 	 --  Agreement.
	 	 	 	 maxNumberOfIterationsPerFrame	 INTEGER  (1 .. 2047)
,
	 	 	 	 -- The average number multiplied with 1000. The average shall be calculated for the
	 	 	 	 --  most recent n frames processed. The value of n shall be documented in the ServiceAgreement.
	 	 	 	 averageNumberOfIterationsPerFrame	 INTEGER  (1000 .. 2047000)
	 	 	 }

,
	 	 	 -- Ratio valid for the most recent n frames processed. The value of n shall be documented
	 	 	 --  in the Service Agreement.
	 	 	 ratioBadFramesToTotalCountOfFramesInTheSample	 REAL (0 .. 1)
	 	 }

	 }

}



-- This event notifies any change of the flfSyncDecResourceStat parameter and the value
--  of flfSyncResourceStat that applies since the event has occurred.
flfSyncDecResourceStatChangeEventOid	 OBJECT IDENTIFIER ::= { 1 3 112 4 4 2 1 30300 2 1 1 }




-- The event value reports the flfSyncResourceStat value that applies since the notified
--  flfSyncResourceStatChange event occurred.
flfSyncDecResourceStatChangeEventValueValueOid	 OBJECT IDENTIFIER ::= { 1 3 112 4 4 2 1 30300 2 1 1 1 }

FlfSyncDecResourceStatChangeEventValue	 ::= FlfSyncDecResourceStat


-- This event notifies any change of flfSyncDecFrameSyncLockStat and the value of flfSyncDecFrameSyncLockStat
--  that applies since the event has occurred. 
flfSyncDecFrameSyncLockStatChangeEventOid	 OBJECT IDENTIFIER ::= { 1 3 112 4 4 2 1 30300 2 2 1 }




-- The event value reports the flfSyncFrameSyncLockStatValue that applies since the
--  notified flfSyncFrameSyncLockStatChange event occurred.
flfSyncDecFrameSyncLockStatChangeEventValueValueOid	 OBJECT IDENTIFIER ::= { 1 3 112 4 4 2 1 30300 2 2 1 1 }

FlfSyncDecFrameSyncLockStatChangeEventValue	 ::= FlfSyncDecFrameSyncLockStat


-- This directive permits setting of the controllable parameters of the FlfSyncAndChnlDecode
--  FR type.  
flfSyncDecSetContrParamsDirectiveOid	 OBJECT IDENTIFIER ::= { 1 3 112 4 4 2 1 30300 3 1 1 }




-- The directive qualifier specifies the FR instance the directive shall act on and
--  contains a set of parameter identifier and parameter value pairs. To be valid, the
--  parameter identifier must reference a controllable parameter of the FlfSyncAndChnlDecode
--  FR and the parameter value must be of the same type as the parameter value that
--  shall be set.
flfSyncDecContrParamIdsAndValuesQualifierOid	 OBJECT IDENTIFIER ::= { 1 3 112 4 4 2 1 30300 3 1 1 1 }

FlfSyncDecContrParamIdsAndValues	 ::= DirectiveQualifier


-- This FR accepts TC frames without FECF belonging to one Master Channel.
-- It provides
--  all TC frames for one physical channel which optionally contain FECFs.
tcMcMuxFrOid	 OBJECT IDENTIFIER ::= { 1 3 112 4 4 2 1 40100 }




-- This enumerated parameter reports the TcMcMux resource status and can take on four
--  values:
-- - 'configured';
-- - 'operational';
-- - 'interrupted';
-- - 'halted'.
tcMcMuxResourceStatParamOid	 OBJECT IDENTIFIER ::= { 1 3 112 4 4 2 1 40100 1 1 1 1 }

TcMcMuxResourceStat 	 ::= ResourceStat


-- This parameter configures and reports the maximum number of TC MC frames that may
--  be converted into a single CLTU. 
tcMcMuxMaxNumberOfFramesPerCltuParamOid	 OBJECT IDENTIFIER ::= { 1 3 112 4 4 2 1 40100 1 2 1 1 }

TcMcMuxMaxNumberOfFramesPerCltu	 ::= INTEGER  (1 .. 15)


-- This parameter configures and reports the maximum length in octets of a TC MC frame
--  the FR accepts for further processing. The reported length refers to the frame length
--  after insertion of the Frame Error Control Field if applicable. 
tcMcMuxMaxFrameLengthParamOid	 OBJECT IDENTIFIER ::= { 1 3 112 4 4 2 1 40100 1 3 1 1 }

-- The engineering unit of this parameter is octet.
TcMcMuxMaxFrameLength	 ::= INTEGER  (1 .. 1024)


-- This parameter configures and reports how the TC Master Channels are multiplexed
--  onto the physical channel. 
-- In case tcMcMuxContr =  ‘fifo’, no further specification
--  applies. 
-- If tcMcMuxContr = 'absolute priority', then the associated configuration
--  value is a sequence of the SCIDs used on the telecommand link where the first SCID
--  in the sequence has the highest priority, the second has the second-highest priority
--  etc. Consequently the sequence has as many elements as Spacecraft Identifiers are
--  permitted on the given physical channel. 
-- If tcMcMuxContr = 'polling vector', then
--  the associated sequence consists of up to 3072 elements where each element is a
--  SCID. 
tcMcMuxContrParamOid	 OBJECT IDENTIFIER ::= { 1 3 112 4 4 2 1 40100 1 4 1 1 }

TcMcMuxContr        	 ::= CHOICE
{
	 fifo                	 [0]	 	 NULL
,	 absolutePriority    	 [1]	 	 SEQUENCE  (SIZE( 1 .. 1024))  OF	 INTEGER 
,	 pollingVector       	 [2]	 	 SEQUENCE  (SIZE( 1 .. 3072))  OF	 INTEGER  (0 .. 1023)
}



-- This enumerated parameter configures and reports if the FR inserts the Frame Error
--  Control Field into each frame before passing it to the TcPlopSyncAndChnlEncode FR.
--  This parameter can take on two values:
-- - 'absent';
-- - 'present'.
-- The details regarding
--  the FEC are specified in CCSDS 232.0-B-2. 
tcMcMuxPresenceOfFecParamOid	 OBJECT IDENTIFIER ::= { 1 3 112 4 4 2 1 40100 1 5 1 1 }

TcMcMuxPresenceOfFec	 ::= ENUMERATED
{
	 absent              	 	 (0)
,	 present             	 	 (1)
}



-- This event notifies any change of the tcMcMuxResourceStat.
tcMcMuxResourceStatChangeEventOid	 OBJECT IDENTIFIER ::= { 1 3 112 4 4 2 1 40100 2 1 1 }




-- The event value reports the tcMcMuxResourceStat value that applies since the notified
--  tcMcMuxResourceStatChange event has occurred.
tcMcMuxResourceStatChangeEventValueValueOid	 OBJECT IDENTIFIER ::= { 1 3 112 4 4 2 1 40100 2 1 1 1 }

TcMcMuxResourceStatChangeEventValue	 ::= TcMcMuxResourceStat


-- This directive permits setting of the controllable parameters of the TcMcMux FR type.
--   
tcMcMuxSetContrParamsDirectiveOid	 OBJECT IDENTIFIER ::= { 1 3 112 4 4 2 1 40100 3 1 1 }




-- The directive qualifier specifies the FR instance the directive shall act on and
--  contains a set of parameter identifier and parameter value pairs. To be valid, the
--  parameter identifier must reference a controllable parameter of the TcMcMux FR and
--  the parameter value must be of the same type as the parameter value that shall be
--  set.
-- 
tcMcMuxContrParamIdsAndValuesQualifierOid	 OBJECT IDENTIFIER ::= { 1 3 112 4 4 2 1 40100 3 1 1 1 }

TcMcMuxContrParamIdsAndValues	 ::= DirectiveQualifier


-- When receiving this directive, the FR discards all data units buffered at that time
--  for the master channel multiplexing.
tcMcMuxDiscardDataUnitsDirectiveOid	 OBJECT IDENTIFIER ::= { 1 3 112 4 4 2 1 40100 3 2 1 }




-- The qualifier of this directive only identifies the Functional Resource instance
--  the directive shall act on, but does not specify any parameter and value that shall
--  be set.
tcMcMuxDiscardDataUnitsQualifierQualifierOid	 OBJECT IDENTIFIER ::= { 1 3 112 4 4 2 1 40100 3 2 1 1 }

TcMcMuxDiscardDataUnitsQualifier	 ::= SEQUENCE
{
	 functResourceInstanceNumber	 INTEGER  (1 .. 4294967295)
,	 serviceInstanceId   	 CHOICE
	 {
	 	 sleServiceInstanceId	 [0]	 	 SleSvcInstanceId
,	 	 cstsServiveInstanceId	 [1]	 	 CstsSvcInstanceId
	 }

}



-- This FR accepts TC frames not containing FECFs for a specific TC VC as input.
-- It
--  provides the TC frames not containing FECFs for a specific TC Master Channel.
tcVcMuxFrOid	 OBJECT IDENTIFIER ::= { 1 3 112 4 4 2 1 40101 }




-- This enumerated parameter reports on the TC VC Multiplexer resource status and can
--  take on four values:
-- - 'configured';
-- - 'operational';
-- - 'interrupted';
-- - 'halted'.
tcVcMuxResourceStatParamOid	 OBJECT IDENTIFIER ::= { 1 3 112 4 4 2 1 40101 1 1 1 1 }

TcVcMuxResourceStat 	 ::= ResourceStat


-- This parameter configures and reports on the maximum TC VC frame length in octets
--  that the FR accepts as input for further processing where the specified length shall
--  not take into account the Frame Error Control Field, if present on the physical
--  channel.
-- Note: The value of the tcVcMaxFrameLength parameter of an instance of
--  this FR must be less than or equal to the parameter tcMcMuxMaxFrameLength of the
--  TcMcMux FR consuming the TC MC frames generated by this TcVcMux FR instance.
tcVcMuxMaxFrameLengthParamOid	 OBJECT IDENTIFIER ::= { 1 3 112 4 4 2 1 40101 1 2 1 1 }

TcVcMuxMaxFrameLength	 ::= INTEGER  (1 .. 1024)


-- This parameter configures and reports how an AD frame on the given Virtual Channel
--  shall be annotated in terms of number of times it shall be transmitted to the spacecraft.
--  
tcVcMuxAdFrameRepetitionsParamOid	 OBJECT IDENTIFIER ::= { 1 3 112 4 4 2 1 40101 1 3 1 1 }

TcVcMuxAdFrameRepetitions	 ::= SEQUENCE  (SIZE( 1 .. 64))  OF	 SEQUENCE
	 {
	 	 vcid                	 INTEGER  (0 .. 63)
,	 	 repetitions         	 INTEGER  (1 .. 5)
	 }



-- This parameter configures and reports how a BC frame on the given Virtual Channel
--  shall be annotated in terms of number of times it shall be transmitted to the spacecraft.
--  
tcVcMuxBcFrameRepetitionsParamOid	 OBJECT IDENTIFIER ::= { 1 3 112 4 4 2 1 40101 1 4 1 1 }

TcVcMuxBcFrameRepetitions	 ::= SEQUENCE  (SIZE( 1 .. 64))  OF	 SEQUENCE
	 {
	 	 vcid                	 INTEGER  (0 .. 63)
,	 	 repetitions         	 INTEGER  (1 .. 5)
	 }



-- This parameter configures and reports the Master Channel that is provided by the
--  given FR instance. The Master Channel ID is the concatenation of TFVN and SCID.
--  Given that this FR type handles only TC frames, the TFVN is fixed and only the SCID
--  is variable. 
tcVcMuxMcParamOid	 OBJECT IDENTIFIER ::= { 1 3 112 4 4 2 1 40101 1 5 1 1 }

TcVcMuxMc           	 ::= SEQUENCE
{
	 tfvn                	 INTEGER  (0)
,	 scid                	 INTEGER  (0 .. 1023)
}



-- This parameter configures and reports how the Virtual Channels are multiplexed into
--  the Master Channel formed by this FR instance. 
-- In case tcVcMuxContr = ‘fifo’,
--  no further specification applies.
-- If tcVcMuxContr = 'absolute priority', then the
--  associated configuration value is a sequence of VCIDs used on the given MC where
--  the first VCID in the sequence has the highest priority, the second has the second-highest
--  priority etc. Consequently the sequence has as many elements as VCs are permitted
--  on the given MC. 
-- If tcVcMuxContr = 'polling vector', then the associated sequence
--  consists of up to 192 elements where each element is a VCID.
tcVcMuxContrParamOid	 OBJECT IDENTIFIER ::= { 1 3 112 4 4 2 1 40101 1 6 1 1 }

TcVcMuxContr        	 ::= CHOICE
{
	 fifo                	 [0]	 	 NULL
,	 absolutePriority    	 [1]	 	 SEQUENCE  (SIZE( 1 .. 64))  OF	 INTEGER  (0 .. 63)
,	 pollingVector       	 [2]	 	 SEQUENCE  (SIZE( 1 .. 192))  OF	 INTEGER  (0 .. 63)
}



-- This event notifies any change of the tcVcMuxResourceStat.
tcVcMuxResourceStatChangeEventOid	 OBJECT IDENTIFIER ::= { 1 3 112 4 4 2 1 40101 2 1 1 }




-- The event value reports the tcVcMuxResourceStat value that applies since the notified
--  tcVcMuxResourceStatChange event has occurred.
tcVcMuxResourceStatChangeEventValueValueOid	 OBJECT IDENTIFIER ::= { 1 3 112 4 4 2 1 40101 2 1 1 1 }

TcVcMuxResourceStatChangeEventValue	 ::= TcVcMuxResourceStat


-- This directive permits setting of the controllable parameters of the TcVcMux FR type.
--   
tcVcMuxSetContrParamsDirectiveOid	 OBJECT IDENTIFIER ::= { 1 3 112 4 4 2 1 40101 3 1 1 }




-- The directive qualifier specifies the FR instance the directive shall act on and
--  contains a set of parameter identifier and parameter value pairs. To be valid, the
--  parameter identifier must reference a controllable parameter of the TcVcMux FR and
--  the parameter value must be of the same type as the parameter value that shall be
--  set.
tcVcMuxContrParamIdsAndValuesQualifierOid	 OBJECT IDENTIFIER ::= { 1 3 112 4 4 2 1 40101 3 1 1 1 }

TcVcMuxContrParamIdsAndValues	 ::= DirectiveQualifier


-- When receiving this directive, the FR discards all data units buffered at that time
--  for the virtual channel multiplexing.
tcVcMuxDiscardDataUnitsDirectiveOid	 OBJECT IDENTIFIER ::= { 1 3 112 4 4 2 1 40101 3 2 1 }




-- The qualifier of this directive only identifies the Functional Resource instance
--  the directive shall act on, but does not specify any parameter and value that shall
--  be set.
tcVcMuxDiscardDataUnitsQualifierQualifierOid	 OBJECT IDENTIFIER ::= { 1 3 112 4 4 2 1 40101 3 2 1 1 }

TcVcMuxDiscardDataUnitsQualifier	 ::= SEQUENCE
{
	 functResourceInstanceNumber	 INTEGER  (1 .. 4294967295)
,	 serviceInstanceId   	 CHOICE
	 {
	 	 sleServiceInstanceId	 [0]	 	 SleSvcInstanceId
,	 	 cstsServiceInstanceId	 [1]	 	 CstsSvcInstanceId
	 }

}



-- This FR instance accepts as input one of the following:
-- - ENCAP.requests carrying
--  IP packets; this type of input data gets converted to Encapsulation packets which
--  are then passed to the VCP service. Such request will only be accepted if (the EPI
--  in the request is 2 and 2 ͼ {valid-protocol-ids)) AND (PVN in the request is 8 AND
--  8 ͼ {valid-packet-version-numbers}).
-- - ENCAP.requests bearing CFDP data units;
--   this type of input data gets converted to Encapsulation packets which are then
--  passed to the VCP service. Such request will only be accepted if (the EPI in the
--  request is 3 AND 3 ͼ {valid-protocol-ids)) AND (the PVN in the request is 8 AND
--  8 ͼ {valid-packet-version-numbers}).
-- - VCP.requests carrying CFDP data units; such
--  request will only be accepted if (the space packet header of the packet in the request
--  has the APID 2045 AND 2045 ͼ {valid-apids}) AND (the PVN in the request is 1 AND
--  1 ͼ {valid-packet-version-numbers}).
-- ENCAP.requests carrying forward file data
--  units; this type of input data gets converted to Encapsulation packets which are
--  then passed to the VCP service. Such request will only be accepted if (the EPI in
--  the request is 7 AND 7 ͼ {valid-protocol-ids}) AND (the PVN in the request is 8
--  AND 8 ͼ {valid-packet-version-numbers}).
-- - VCP.requests carrying space packets;
--  such requests will only be accepted if (the PVN in the request is 1 AND 1 ͼ {valid-packet-version-numbers})
--  and the APID contained in the header of the packet in the request ͼ valid-apids.
-- -
--  MAP Channel frame data units that are the result of MAP multiplexing; this input
--  type is only accepted if presence-of-segment-header = 'present'. 
-- Regardless of
--  the specific input type, incoming requests are only accepted if the VCID of the
--  SDLP Channel / GVCID of the request is equal to tc-frame-vcid and the TVN of the
--  GVCID in the request is 0.
-- In deviation from CCSDS 232.0-B-2, the VCP.requests
--  carrying space packets have an additional argument that flags if the packet of this
--  request may be blocked, i.e. may be embedded in a TC frame together with other space
--  packets or has to the single packet traveling in the given TC frame.
-- In parallel
--  it may accept as input
-- - COP directives;
-- - CLCWs extracted from the associated
--  return link.
-- This FR provides TC frames of a specific Virtual Channel. These frames
--  do not (yet) contain the FECF.
tcEncapVcPktProcVcGenFrOid	 OBJECT IDENTIFIER ::= { 1 3 112 4 4 2 1 40102 }




-- This directive permits setting of the controllable parameters of the TC Encap VC
--  Pkt Processing & VC Gen FR type.  
-- 
tcEncapSetContrParamsDirectiveOid	 OBJECT IDENTIFIER ::= { 1 3 112 4 4 2 1 40102 3 1 1 }



tcMapMuxFrOid	 OBJECT IDENTIFIER ::= { 1 3 112 4 4 2 1 40103 }




-- This FR instance accepts as input one of the following:
-- - ENCAP.requests carrying
--  IP packets; this type of input data gets converted to Encapsulation packets which
--  are then passed to the MAPP service. Such request will only be accepted if (the
--  EPI in the request is 2 and 2 ͼ {valid-protocol-ids)) AND (PVN in the request is
--  8 AND 8 ͼ {valid-packet-version-numbers}) AND the GMAP ID specified in the SDLP
--  Channel of the ENCAP.request identifies a MAP ID that is ͼ {valid-map-ids}
-- - ENCAP.requests
--  bearing CFDP data units;  this type of input data gets converted to Encapsulation
--  packets which are then passed to the MAPP service. Such request will only be accepted
--  if (the EPI in the request is 3 AND 3 ͼ {valid-protocol-ids)) AND (the PVN in the
--  request is 8 AND 8 ͼ {valid-packet-version-numbers}) AND the MAP ID contained in
--  the GMAP ID conveyed in the SDLP_Channel parameter of the ENCAP.request is  ͼ {valid-map-ids}.
-- -
--  MAPP.requests carrying CFDP data units; such request will only be accepted if (the
--  space packet header of the packet in the request has the APID 2045 AND 2045 ͼ {valid-apids})
--  AND (the PVN in the request is 1 AND 1 ͼ {valid-packet-version-numbers}) AND the
--  MAP ID parameter of the MAPP.request is ͼ {valid-map-ids}.
-- ENCAP.requests carrying
--  forward file data units; this type of input data gets converted to Encapsulation
--  packets which are then passed to the VCP service. Such request will only be accepted
--  if (the EPI in the request is 7 AND 7 ͼ {valid-protocol-ids}) AND (the PVN in the
--  request is 8 AND 8 ͼ {valid-packet-version-numbers}).
-- - VCP.requests carrying space
--  packets; such requests will only be accepted if (the PVN in the request is 1 AND
--  1 ͼ {valid-packet-version-numbers}) and the APID contained in the header of the
--  packet in the request ͼ valid-apids.
-- - MAP Channel frame data units that are the
--  result of MAP multiplexing; this input type is only accepted if presence-of-segment-header
--  = 'present'. 
-- Regardless of the specific input type, incoming requests are only
--  accepted if the VCID of the SDLP Channel / GVCID of the request is equal to tc-frame-vcid
--  and the TVN of the GVCID in the request is 0.
-- In deviation from CCSDS 232.0-B-2,
--  the VCP.requests carrying space packets have an additional argument that flags if
--  the packet of this request may be blocked, i.e. may be embedded in a TC frame together
--  with other space packets or has to the single packet traveling in the given TC frame.
-- In
--  parallel it may accept as input
-- - COP directives;
-- - CLCWs extracted from the associated
--  return link.
-- This FR provides TC frames of a specific Virtual Channel. These frames
--  do not (yet) contain the FECF.Note: The present FR Model does not envisage the use
--  of the 
-- MAPA.request primitive as an input to this FR type. Therefore, the 
-- parameters
--  defined for this FR do not cover the case of incoming 
-- MAPA.request primitives.
--  
tcEncapMapPktProcessingFrOid	 OBJECT IDENTIFIER ::= { 1 3 112 4 4 2 1 40104 }




-- This FR accepts AOS frames without FECF belonging to one Master Channel.
-- It provides
--  all AOS frames for one physical channel.which optionally contain FECFs.
aosMcMuxFrOid	 OBJECT IDENTIFIER ::= { 1 3 112 4 4 2 1 40200 }




-- This enumerated parameter reports the AosMcMux FR resource status and can take on
--  four values:
-- -  - 'configured': the associated equipment has been configured
-- 
--     - 'operational': the associated equipment is active;
--     - 'interrupted': a
--  failure has been detected;
--     - 'halted': the associated equipment has been taken
--  out of service.
aosMcMuxResourceStatParamOid	 OBJECT IDENTIFIER ::= { 1 3 112 4 4 2 1 40200 1 1 1 1 }

AosMcMuxResourceStat	 ::= ResourceStat


-- This parameter configures and reports how the AOS Master Channels are multiplexed
--  onto the physical channel. 
-- - If aosMcMuxContr =  ‘fifo’, no further specification
--  applies. 
-- - If aosMcMuxContr = 'absolute priority', then the associated configuration
--  value is a sequence of the SCIDs used on the telecommand link where the first SCID
--  in the sequence has the highest priority, the second has the second-highest priority
--  etc. Consequently the sequence has as many elements as Spacecraft Identifiers are
--  permitted on the given physical channel. 
-- - If aosMcMuxContr = 'polling vector',
--  then the associated sequence consists of up to 768 elements where each element is
--  a SCID. 
aosMcMuxContrParamOid	 OBJECT IDENTIFIER ::= { 1 3 112 4 4 2 1 40200 1 2 1 1 }

AosMcMuxContr       	 ::= CHOICE
{
	 fifo                	 [0]	 	 NULL
,	 absolutePriority    	 [1]	 	 SEQUENCE  (SIZE( 1 .. 256))  OF	 INTEGER  (0 .. 255)
,	 pollingVector       	 [2]	 	 SEQUENCE  (SIZE( 1 .. 768))  OF	 INTEGER  (0 .. 255)
}



-- This enumerated parameter configures and reports if the FR inserts the Header Error
--  Control Field into each AOS frame. This parameter can take on two values:
-- - 'present';
-- -
--  'absent'.
aosMcMuxPresenceOfFrameHeaderErrorContrParamOid	 OBJECT IDENTIFIER ::= { 1 3 112 4 4 2 1 40200 1 3 1 1 }

AosMcMuxPresenceOfFrameHeaderErrorContr	 ::= ENUMERATED
{
	 present             	 	 (0)
,	 absent              	 	 (1)
}



-- This enumerated parameter configures and reports if the FR inserts the Frame Error
--  Control Field into each AOS frame before providing it to the encoding FR. This parameter
--  can take on two values:
-- 
-- - 'present';
-- - 'absent'.
aosMcMuxPresenceOfFrameErrorContrParamOid	 OBJECT IDENTIFIER ::= { 1 3 112 4 4 2 1 40200 1 4 1 1 }

AosMcMuxPresenceOfFrameErrorContr	 ::= ENUMERATED
{
	 present             	 	 (0)
,	 absent              	 	 (1)
}



-- This event notifies any change of the aosMcMuxResourceStat.
aosMcMuxResourceStatChangeEventOid	 OBJECT IDENTIFIER ::= { 1 3 112 4 4 2 1 40200 2 1 1 }




-- The event value reports the aosMcMuxResourceStat value that applies after the resource
--  status of  the aosMcMux resource status has changed.
aosMcMuxResourceStatValueValueOid	 OBJECT IDENTIFIER ::= { 1 3 112 4 4 2 1 40200 2 1 1 1 }

AosMcMuxResourceStatValue	 ::= AosMcMuxResourceStat


-- This event notifies the completion of processing of a data unit. This event is emitted
--  only for data units that are transferred through an instance of a Cross Support
--  Transfer Service (CSTS) that uses the CSTS Specification Framework Data Processing
--  procedure  or a procedure derived from it. Each data unit received from such a CSTS
--  is annotated with the service-instance-id  of the source CSTS instance and the data-unit-id
--  of the PROCESS-DATA invocation that carries that data unit.
aosMcMuxDataUnitProcessingCompletedEventOid	 OBJECT IDENTIFIER ::= { 1 3 112 4 4 2 1 40200 2 2 1 }




-- This parameter contains the data-unit-id of the data unit that has completed processing,
--  and the service-instance -identifier of the CSTS instance through which the data
--  unit was received.
aosMcMuxDataUnitProcessingCompletedValueValueOid	 OBJECT IDENTIFIER ::= { 1 3 112 4 4 2 1 40200 2 2 1 1 }

AosMcMuxDataUnitProcessingCompletedValue	 ::= DataUnitProcessingCompletedEventValue


-- This directive sets the controllable parameters of the AOS MC Mux FR type.  
-- 
aosMcMuxSetContrParamsDirectiveOid	 OBJECT IDENTIFIER ::= { 1 3 112 4 4 2 1 40200 3 1 1 }




-- The directive qualifier specifies the FR instance the directive shall act on and
--  contains a set of parameter identifier and parameter value pairs. To be valid, the
--  parameter identifier must reference a controllable parameter of the AOS MC Mux FR
--  and the parameter value must be of the same type as the parameter value that shall
--  be set. 
aosMcMuxContrParamIdsAndValuesQualifierOid	 OBJECT IDENTIFIER ::= { 1 3 112 4 4 2 1 40200 3 1 1 1 }

AosMcMuxContrParamIdsAndValues	 ::= DirectiveQualifier


-- When receiving this directive, the FR discards all currently buffered data units
--  that have been received through the transfer service instance identified in the
--  directive qualifier.
aosMcMuxDiscardDataUnitsDirectiveOid	 OBJECT IDENTIFIER ::= { 1 3 112 4 4 2 1 40200 3 2 1 }




-- The service-instance-id of the CSTS for which the data units are to discarded when
--  the aosMcMuxDiscardDataUnits directive is invoked.
aosMcMuxDiscardDataUnitsSvcInstanceIdQualifierOid	 OBJECT IDENTIFIER ::= { 1 3 112 4 4 2 1 40200 3 2 1 1 }

AosMcMuxDiscardDataUnitsSvcInstanceId	 ::= CstsSvcInstanceId


-- This FR accepts AOS frames not containing FECFs for a specific AOS VC as input.
-- It
--  provides the AOS frames not containing FECFs for a specific AOS Master Channel.
aosVcMuxFrOid	 OBJECT IDENTIFIER ::= { 1 3 112 4 4 2 1 40201 }




-- This enumerated parameter reports the AosVcMux FR resource status and can take on
--  four values:
-- -  - 'configured': the associated equipment has been configured
-- 
--     - 'operational': the associated equipment is active;
--     - 'interrupted': a
--  failure has been detected;
--     - 'halted': the associated equipment has been taken
--  out of service.
aosVcMuxResourceStatParamOid	 OBJECT IDENTIFIER ::= { 1 3 112 4 4 2 1 40201 1 1 1 1 }

AosVcMuxResourceStat	 ::= ResourceStat


-- This parameter configures and reports the Master Channel that is provided by the
--  given FR instance. The Master Channel ID is the concatenation of TFVN and SCID.
--  Given that this FR type handles only AOS frames, the TFVN is fixed and only the
--  SCID is variable. 
aosVcMuxMcParamOid	 OBJECT IDENTIFIER ::= { 1 3 112 4 4 2 1 40201 1 2 1 1 }

AosVcMuxMc          	 ::= SEQUENCE
{
	 tfvn                	 INTEGER  (1)
,	 scid                	 INTEGER  (0 .. 255)
}



-- This parameter configures and reports how the Virtual Channels are multiplexed into
--  the Master Channel formed by this FR instance. 
-- - If aosVcMuxContr = ‘fifo’, no
--  further specification applies.
-- - If aosVcMuxContr = 'absolute priority', then the
--  associated configuration value is a sequence of VCIDs used on the given MC where
--  the first VCID in the sequence has the highest priority, the second has the second-highest
--  priority etc. Consequently the sequence has as many elements as VCs are permitted
--  on the given MC. 
-- - If aosVcMuxContr = 'polling vector', then the associated sequence
--  consists of up to 192 elements where each element is a VCID.
aosVcMuxContrParamOid	 OBJECT IDENTIFIER ::= { 1 3 112 4 4 2 1 40201 1 3 1 1 }

AosVcMuxContr       	 ::= CHOICE
{
	 fifo                	 [0]	 	 NULL
,	 absolutePriority    	 [1]	 	 SEQUENCE  (SIZE( 1 .. 64))  OF	 INTEGER  (0 .. 63)
,	 pollingVector       	 [2]	 	 SEQUENCE  (SIZE( 1 .. 192))  OF	 INTEGER  (0 .. 63)
}



-- This event notifies any change of the aosVcMuxResourceStat.
aosVcMuxResourceStatChangeEventOid	 OBJECT IDENTIFIER ::= { 1 3 112 4 4 2 1 40201 2 1 1 }




-- The event value reports the aosVcMuxResourceStat value that applies after the resource
--  status of  the aosVcMux resource status has changed.
aosVcMuxResourceStatValueValueOid	 OBJECT IDENTIFIER ::= { 1 3 112 4 4 2 1 40201 2 1 1 1 }

AosVcMuxResourceStatValue	 ::= AosVcMuxResourceStat


-- This event notifies the completion of processing of a data unit. This event is emitted
--  only for data units that are transferred through an instance of a Cross Support
--  Transfer Service (CSTS) that uses the CSTS Specification Framework Data Processing
--  procedure  or a procedure derived from it. Each data unit received from such a CSTS
--  is annotated with the service-instance-id  of the source CSTS instance and the data-unit-id
--  of the PROCESS-DATA invocation that carries that data unit.
aosVcMuxDataUnitProcessingCompletedEventOid	 OBJECT IDENTIFIER ::= { 1 3 112 4 4 2 1 40201 2 2 1 }




-- This parameter contains the data-unit-id of the data unit that has completed processing,
--  and the service-instance-identifier of the CSTS instance through which the data
--  unit was received.
aosVcMuxDataUnitProcessingCompletedValueValueOid	 OBJECT IDENTIFIER ::= { 1 3 112 4 4 2 1 40201 2 2 1 1 }

AosVcMuxDataUnitProcessingCompletedValue	 ::= DataUnitProcessingCompletedEventValue


-- This directive sets the controllable parameters of the AosVcMuxFR type.
aosVcMuxSetContrParamsDirectiveOid	 OBJECT IDENTIFIER ::= { 1 3 112 4 4 2 1 40201 3 1 1 }




-- The directive qualifier specifies the FR instance the directive shall act on and
--  contains a set of parameter identifier and parameter value pairs. To be valid, the
--  parameter identifier must reference a controllable parameter of the AOS VC Mux FR
--  and the parameter value must be of the same type as the parameter value that shall
--  be set. 
aosVcMuxContrParamIdsAndValuesQualifierOid	 OBJECT IDENTIFIER ::= { 1 3 112 4 4 2 1 40201 3 1 1 1 }

AosVcMuxContrParamIdsAndValues	 ::= DirectiveQualifier


-- When receiving this directive, the FR discards all currently buffered data units
--  that have been received through the transfer service instance identified in the
--  directive qualifier.
aosVcMuxDiscardDataUnitsDirectiveOid	 OBJECT IDENTIFIER ::= { 1 3 112 4 4 2 1 40201 3 2 1 }




-- The service-instance-id of the CSTS for which the data units are to discarded when
--  the aosVcMuxDiscardDataUnits directive is invoked.
aosVcMuxDiscardDataUnitsSvcInstanceIdQualifierOid	 OBJECT IDENTIFIER ::= { 1 3 112 4 4 2 1 40201 3 2 1 1 }

AosVcMuxDiscardDataUnitsSvcInstanceId	 ::= CstsSvcInstanceId


-- TBS (not part of T1 or T2). NOTE that the paremeter of this FR are currently just
--  placeholders.
aosEncapPktProcAndVcGenFrOid	 OBJECT IDENTIFIER ::= { 1 3 112 4 4 2 1 40202 }




-- To be defined
vlfUslpMcMuxFrOid	 OBJECT IDENTIFIER ::= { 1 3 112 4 4 2 1 40300 }




-- To be defined
vlfUslpVcMuxFrOid	 OBJECT IDENTIFIER ::= { 1 3 112 4 4 2 1 40301 }




-- To be defined
vlfUslpVcGenFrOid	 OBJECT IDENTIFIER ::= { 1 3 112 4 4 2 1 40302 }




-- To be defined.
uslpMapMuxFrOid	 OBJECT IDENTIFIER ::= { 1 3 112 4 4 2 1 40303 }




-- To be defined
uslpEncapMapPktProcessingFrOid	 OBJECT IDENTIFIER ::= { 1 3 112 4 4 2 1 40304 }




-- This FR accepts fixed-length USLP frames without FECF belonging to one Master Channel.
-- It
--  provides all fixed-length USLP frames for one physical channel.which optionally
--  contain FECFs.
flfUslpMcMuxFrOid	 OBJECT IDENTIFIER ::= { 1 3 112 4 4 2 1 40400 }




-- This enumerated parameter reports the FlfUslpMcMux FR resource status and can take
--  on four values:
-- -  - 'configured': the associated equipment has been configured
-- 
--     - 'operational': the associated equipment is active;
--     - 'interrupted': a
--  failure has been detected;
--     - 'halted': the associated equipment has been taken
--  out of service.
flfUslpMcMuxResourceStatParamOid	 OBJECT IDENTIFIER ::= { 1 3 112 4 4 2 1 40400 1 1 1 1 }

FlfUslpMcMuxResourceStat	 ::= ResourceStat


-- This parameter configures and reports how the USLP Master Channels are multiplexed
--  onto the physical channel. 
-- - If flfUslpMcMuxContr =  ‘fifo’, no further specification
--  applies. 
-- - If flfUslpMcMuxContr = 'absolute priority', then the associated configuration
--  value is a sequence of the SCIDs used on the telecommand link where the first SCID
--  in the sequence has the highest priority, the second has the second-highest priority
--  etc. Consequently the sequence has as many elements as Spacecraft Identifiers are
--  permitted on the given physical channel. 
-- - If flfUslpMcMuxContr = 'polling vector',
--  then the associated sequence consists of up to 768 elements where each element is
--  a SCID. 
flfUslpMcMuxContrParamOid	 OBJECT IDENTIFIER ::= { 1 3 112 4 4 2 1 40400 1 2 1 1 }

FlfUslpMcMuxContr   	 ::= UslpMcMuxContr


-- This parameter configures and reports if the FR inserts the Frame Error Control Field
--  into each USLP frame before providing it to the encoding FR, and if so, then length
--  of that FECF (in octets). This parameter can take on three values:
-- 
-- - 0;
-- - 2;
--  or
-- - 4
-- where the value 0 (zero) indicates that the FECF is absent from the frames.
flfUslpMcMuxFrameErrorContrLengthParamOid	 OBJECT IDENTIFIER ::= { 1 3 112 4 4 2 1 40400 1 3 1 1 }

FlfUslpMcMuxFrameErrorContrLength	 ::= INTEGER  (0 | 2 | 4)


-- This event notifies the completion of processing of a data unit. This event is emitted
--  only for data units that are transferred through an instance of a Cross Support
--  Transfer Service (CSTS) that uses the CSTS Specification Framework Data Processing
--  procedure  or a procedure derived from it. Each data unit received from such a CSTS
--  is annotated with the service-instance-id  of the source CSTS instance and the data-unit-id
--  of the PROCESS-DATA invocation that carries that data unit.
flfUslpMcMuxDataUnitProcessingCompletedEventOid	 OBJECT IDENTIFIER ::= { 1 3 112 4 4 2 1 40400 2 1 1 }




-- This parameter contains the data-unit-id of the data unit that has completed processing,
--  and the service-instance -identifier of the CSTS instance through which the data
--  unit was received.
flfUslpMcMuxDataUnitProcessingCompletedValueValueOid	 OBJECT IDENTIFIER ::= { 1 3 112 4 4 2 1 40400 2 1 1 1 }

FlfUslpMcMuxDataUnitProcessingCompletedValue	 ::= DataUnitProcessingCompletedEventValue


-- This event notifies any change of the flfUslpMcMuxResourceStat.
flfUslpMcMuxResourceStatChangeEventOid	 OBJECT IDENTIFIER ::= { 1 3 112 4 4 2 1 40400 2 2 1 }




-- The event value reports the aosMcMuxResourceStat value that applies after the resource
--  status of  the aosMcMux resource status has changed.
flfUslpMcMuxResourceStatValueValueOid	 OBJECT IDENTIFIER ::= { 1 3 112 4 4 2 1 40400 2 2 1 1 }

FlfUslpMcMuxResourceStatValue	 ::= FlfUslpMcMuxResourceStat


-- This directive sets the controllable parameters of the FlfUslpMcMux type.  
-- 
flfUslpMcMuxSetContrParamsDirectiveOid	 OBJECT IDENTIFIER ::= { 1 3 112 4 4 2 1 40400 3 1 1 }




-- The directive qualifier specifies the FR instance the directive shall act on and
--  contains a set of parameter identifier and parameter value pairs. To be valid, the
--  parameter identifier must reference a controllable parameter of the FLF USLP MC
--  Mux FR and the parameter value must be of the same type as the parameter value that
--  shall be set. 
flfUslpMcMuxSetContrParamIdsAndValuesQualifierOid	 OBJECT IDENTIFIER ::= { 1 3 112 4 4 2 1 40400 3 1 1 1 }

FlfUslpMcMuxSetContrParamIdsAndValues	 ::= DirectiveQualifier


-- When receiving this directive, the FR discards all currently buffered data units
--  that have been received through the transfer service instance identified in the
--  directive qualifier.
flfUslpMcMuxDiscardDataUnitsDirectiveOid	 OBJECT IDENTIFIER ::= { 1 3 112 4 4 2 1 40400 3 2 1 }




-- The service-instance-id of the CSTS for which the data units are to discarded when
--  the flfUslpMcMuxDiscardDataUnits directive is invoked.
flfUslpMcMuxDiscardDataUnitsSvcInstanceIdQualifierOid	 OBJECT IDENTIFIER ::= { 1 3 112 4 4 2 1 40400 3 2 1 1 }

FlfUslpMcMuxDiscardDataUnitsSvcInstanceId	 ::= CstsSvcInstanceId


-- This FR accepts fixed-length USLP frames not containing FECFs for a specific USLP
--  VC as input.
-- It provides the USLP frames not containing FECFs for a specific USLP
--  Master Channel.
flfUslpVcMuxFrOid	 OBJECT IDENTIFIER ::= { 1 3 112 4 4 2 1 40401 }




-- This enumerated parameter reports the FlfUslpMcMux FR resource status and can take
--  on four values:
-- -  - 'configured': the associated equipment has been configured
-- 
--     - 'operational': the associated equipment is active;
--     - 'interrupted': a
--  failure has been detected;
--     - 'halted': the associated equipment has been taken
--  out of service.
flfUslpVcMuxResourceStatParamOid	 OBJECT IDENTIFIER ::= { 1 3 112 4 4 2 1 40401 1 1 1 1 }

FlfUslpVcMuxResourceStat	 ::= ResourceStat


-- This parameter configures and reports the Master Channel that is provided by the
--  given FR instance. The Master Channel ID is the concatenation of TFVN and SCID.
--  Given that this FR type handles only USLP frames, the TFVN is fixed and only the
--  SCID is variable. 
flfUslpVcMuxMcParamOid	 OBJECT IDENTIFIER ::= { 1 3 112 4 4 2 1 40401 1 2 1 1 }

FlfUslpVcMuxMc      	 ::= UslpVcMuxMc


-- This parameter configures and reports how the Virtual Channels are multiplexed into
--  the Master Channel formed by this FR instance. 
-- - If flfUslpVcMuxContr = ‘fifo’,
--  no further specification applies.
-- - If flfUslpVcMuxContr = 'absolute priority',
--  then the associated configuration value is a sequence of VCIDs used on the given
--  MC where the first VCID in the sequence has the highest priority, the second has
--  the second-highest priority etc. Consequently the sequence has as many elements
--  as VCs are permitted on the given MC. 
-- - If flfUslpVcMuxContr = 'polling vector',
--  then the associated sequence consists of up to 192 elements where each element is
--  a VCID.
flfUslpVcMuxContrParamOid	 OBJECT IDENTIFIER ::= { 1 3 112 4 4 2 1 40401 1 3 1 1 }

FlfUslpVcMuxContr   	 ::= UslpVcMuxContr


-- This event notifies any change of the flfUslpVcMuxResourceStat.
flfUslpVcMuxResourceStatChangeEventOid	 OBJECT IDENTIFIER ::= { 1 3 112 4 4 2 1 40401 2 1 1 }




-- The event value reports the flfUslpVcMuxResourceStat value that applies after the
--  resource status of the flfUslpVcMux resource status has changed.
flfUslpVcMuxResourceStatValueValueOid	 OBJECT IDENTIFIER ::= { 1 3 112 4 4 2 1 40401 2 1 1 1 }

FlfUslpVcMuxResourceStatValue	 ::= FlfUslpVcMuxResourceStat


-- This event notifies the completion of processing of a data unit. This event is emitted
--  only for data units that are transferred through an instance of a Cross Support
--  Transfer Service (CSTS) that uses the CSTS Specification Framework Data Processing
--  procedure  or a procedure derived from it. Each data unit received from such a CSTS
--  is annotated with the service-instance-id  of the source CSTS instance and the data-unit-id
--  of the PROCESS-DATA invocation that carries that data unit.
flfUslpVcMuxDataUnitProcessingCompletedEventOid	 OBJECT IDENTIFIER ::= { 1 3 112 4 4 2 1 40401 2 2 1 }




-- This parameter contains the data-unit-id of the data unit that has completed processing,
--  and the service-instance -identifier of the CSTS instance through which the data
--  unit was received.
flf-UslpVcMuxDataUnitProcessingCompletedValueValueOid	 OBJECT IDENTIFIER ::= { 1 3 112 4 4 2 1 40401 2 2 1 1 }

Flf-UslpVcMuxDataUnitProcessingCompletedValue	 ::= DataUnitProcessingCompletedEventValue


-- This directive sets the controllable parameters of the FLF USLP VC Mux FR type.
flfUslpVcMuxSetContrParamsDirectiveOid	 OBJECT IDENTIFIER ::= { 1 3 112 4 4 2 1 40401 3 1 1 }




-- The directive qualifier specifies the FR instance the directive shall act on and
--  contains a set of parameter identifier and parameter value pairs. To be valid, the
--  parameter identifier must reference a controllable parameter of the FLF USLP VC
--  Mux FR and the parameter value must be of the same type as the parameter value that
--  shall be set. 
flfUslpVcMuxContrParamIdsAndValuesQualifierOid	 OBJECT IDENTIFIER ::= { 1 3 112 4 4 2 1 40401 3 1 1 1 }

FlfUslpVcMuxContrParamIdsAndValues	 ::= DirectiveQualifier


-- When receiving this directive, the FR discards all currently buffered data units
--  that have been received through the transfer service instance identified in the
--  directive qualifier.
flfUslpVcMuxDiscardDataUnitsDirectiveOid	 OBJECT IDENTIFIER ::= { 1 3 112 4 4 2 1 40401 3 2 1 }




-- The service-instance-id of the CSTS for which the data units are to discarded when
--  the flfUslpVcMuxDiscardDataUnits directive is invoked.
flfUslpVcMuxDiscardDataUnitsSvcInstanceIdQualifierOid	 OBJECT IDENTIFIER ::= { 1 3 112 4 4 2 1 40401 3 2 1 1 }

FlfUslpVcMuxDiscardDataUnitsSvcInstanceId	 ::= CstsSvcInstanceId


-- TBS (not part of T1 or T2)
flfUslpVcGenFrOid	 OBJECT IDENTIFIER ::= { 1 3 112 4 4 2 1 40402 }




-- TBS (not part of T1 or T2)
flfUslpMapMuxFrOid	 OBJECT IDENTIFIER ::= { 1 3 112 4 4 2 1 40403 }




-- TBS (not part of T1 or T2)
flfUslpEncapMapPktProcessingFrOid	 OBJECT IDENTIFIER ::= { 1 3 112 4 4 2 1 40404 }




-- The TmAosMcDemux FR accepts suceessfully decoded frames and passes on all frames
--  of the configured Master Channels. If so configured it also extracts and delivers
--  the CLCWs of the selected Master Channel. 
tmAosMcDemuxFrOid	 OBJECT IDENTIFIER ::= { 1 3 112 4 4 2 1 40500 }




-- This enumerated parameter reports the tmAosMcDemux FR resource status and can take
--  on four values:
-- - 'configured'; 
-- - 'operational';
-- - 'interrupted';
-- - 'halted'.
tmAosMcDemuxResourceStatParamOid	 OBJECT IDENTIFIER ::= { 1 3 112 4 4 2 1 40500 1 1 1 1 }

TmAosMcDemuxResourceStat	 ::= ResourceStat


-- This parameter reports the Master Channel IDs the given FR instance is configured
--  to process.
tmAosMcDemuxMcIdsParamOid	 OBJECT IDENTIFIER ::= { 1 3 112 4 4 2 1 40500 1 2 1 1 }

-- All frames on a Master Channel must have the same TFVN.
TmAosMcDemuxMcIds   	 ::= CHOICE
{
	 tmFrames            	 [0]	 	 SET  (SIZE( 1 .. 1024))  OF	 SEQUENCE
	 	 {

	 	 	 -- For Tm frames the Transfer Frame Version Number is always 0.
	 	 	 tfvn                	 INTEGER  (0)
,	 	 	 scid                	 INTEGER  (0 .. 1023)
	 	 }

,	 aosFrames           	 [1]	 	 SET  (SIZE( 1 .. 256))  OF	 SEQUENCE
	 	 {

	 	 	 -- For AOS frames the Transfer Frame Version Number is always 1.
	 	 	 tfvn                	 INTEGER  (1)
,	 	 	 scid                	 INTEGER  (0 .. 255)
	 	 }

}



-- This enumerated parameter configures and reports if the FR instance shall extract
--  CLCWs and if so from which MC. The extracted CLCWs are forwarded to the FR types
--  that consume them.
-- 
tmAosMcDemuxClcwExtractionParamOid	 OBJECT IDENTIFIER ::= { 1 3 112 4 4 2 1 40500 1 3 1 1 }

TmAosMcDemuxClcwExtraction	 ::= CHOICE
{
	 noClcwExtraction    	 [0]	 	 NULL
,	 clcwExtractionTmMc  	 [1]	 	 SEQUENCE
	 {

	 	 -- For Tm frames the Transfer Frame Version Number is always 0.
	 	 tfvn                	 INTEGER  (0)
,	 	 scid                	 INTEGER  (0 .. 1023)
	 }

,	 clcwExtractionAosMc 	 [2]	 	 SEQUENCE
	 {

	 	 -- For AOS frames the Transfer Frame Version Number is always 1.
	 	 tfvn                	 INTEGER  (1)
,	 	 scid                	 INTEGER  (0 .. 255)
	 }

}



-- This event notifies any change of the tmAosMcDemuxResourceStat parameter.
tmAosMcDemuxResourceStatChangeEventOid	 OBJECT IDENTIFIER ::= { 1 3 112 4 4 2 1 40500 2 1 1 }




-- The event value reports the tmAosMcDemuxResourceStat value that applies since the
--  notified tmAosMcDemuxResourceStatChange event occurred.
tmAosMcDemuxResourceStatChangeEventValueValueOid	 OBJECT IDENTIFIER ::= { 1 3 112 4 4 2 1 40500 2 1 1 1 }

TmAosMcDemuxResourceStatChangeEventValue	 ::= TmAosMcDemuxResourceStat


-- This directive permits setting of the controllable parameters of the TmAosMcDemux
--  FR type. 
tmAosMcDemuxSetContrParamsDirectiveOid	 OBJECT IDENTIFIER ::= { 1 3 112 4 4 2 1 40500 3 1 1 }




-- The directive qualifier specifies the FR instance the directive shall act on and
--  contains a set of parameter identifier and parameter value pairs. To be valid, the
--  parameter identifier must reference a controllable parameter of the TmAoasMcDemux
--  FR and the parameter value must be of the same type as the parameter value that
--  shall be set.
-- 
tmAosMcDemuxContrParamIdsAndValuesQualifierOid	 OBJECT IDENTIFIER ::= { 1 3 112 4 4 2 1 40500 3 1 1 1 }

TmAosMcDemuxContrParamIdsAndValues	 ::= DirectiveQualifier


-- The TmAosVcDemux FR accepts frames from a given master channel and passes on all
--  frames of the configured Virtual Channels. If so configured it also extracts and
--  delivers the CLCWs of the selected Virtual Channel. 
tmAosVcDemuxFrOid	 OBJECT IDENTIFIER ::= { 1 3 112 4 4 2 1 40501 }




-- This enumerated parameter reports the TmAosVcDemux FR resource status and can take
--  on four values:
-- - 'configured'; 
-- - 'operational';
-- - 'interrupted';
-- - 'halted'.
tmAosVcDemuxResourceStatParamOid	 OBJECT IDENTIFIER ::= { 1 3 112 4 4 2 1 40501 1 1 1 1 }

TmAosVcDemuxResourceStat	 ::= ResourceStat


-- This parameter configures and reports the Virtual Channel IDs the given FR instance
--  is configured to process. 
tmAosVcDemuxVcIdParamOid	 OBJECT IDENTIFIER ::= { 1 3 112 4 4 2 1 40501 1 2 1 1 }

TmAosVcDemuxVcId    	 ::= CHOICE
{
	 tmFrames            	 [0]	 	 SET  (SIZE( 1 .. 8))  OF	 INTEGER  (0 .. 7)
,	 aosFrames           	 [1]	 	 SET  (SIZE( 1 .. 256))  OF	 INTEGER  (0 .. 255)
}



-- This parameter configures and reports if the FR instance shall extract CLCWs and
--  if so from which VC. The extracted CLCWs are forwarded  to the FR types that consume
--  them. 
tmAosVcDemuxClcwExtractionParamOid	 OBJECT IDENTIFIER ::= { 1 3 112 4 4 2 1 40501 1 3 1 1 }

TmAosVcDemuxClcwExtraction	 ::= CHOICE
{
	 noClcwExtraction    	 [0]	 	 NULL
,	 clcwExtractionTmVc  	 [1]	 	 SEQUENCE
	 {

	 	 -- For Tm frames the Transfer Frame Version Number is always 0.
	 	 tfvn                	 INTEGER  (0)
,	 	 scid                	 INTEGER  (0 .. 1023)
,	 	 vcid                	 INTEGER  (0 .. 7)
	 }

,	 clcwExtractionAosVc 	 [2]	 	 SEQUENCE
	 {

	 	 -- For AOS frames the Transfer Frame Version Number is always 1.
	 	 tfvn                	 INTEGER  (0)
,	 	 scid                	 INTEGER  (0 .. 255)
,	 	 vcid                	 INTEGER  (0 .. 63)
	 }

}



-- This parameter reports the GVCIDs of the frames being delivered by this FR instance.
--  The Master Channel Id being part of the GVCID is redundant in the sense that it
--  is determined by the configuration of the TmAosMcDemux FR delivering frames to the
--  given tmAosVcDemux FR instance. However, the GVCID is a frequently used parameter
--  and is provided by the TmAosVcDemux FR for convenience.
tmAosVcDemuxGvcidParamOid	 OBJECT IDENTIFIER ::= { 1 3 112 4 4 2 1 40501 1 4 1 1 }

TmAosVcDemuxGvcid   	 ::= CHOICE
{
	 tmGvcid             	 [0]	 	 SET  (SIZE( 1 .. 8))  OF	 SEQUENCE
	 	 {

	 	 	 -- For Tm frames the Transfer Frame Version Number is always 0.
	 	 	 tfvn                	 INTEGER  (0)
,	 	 	 scid                	 INTEGER  (0 .. 1023)
,	 	 	 vcid                	 INTEGER  (0 .. 7)
	 	 }

,	 aosGvcid            	 [1]	 	 SET  (SIZE( 1 .. 64))  OF	 SEQUENCE
	 	 {

	 	 	 -- For AOS frames the Transfer Frame Version Number is always 1.
	 	 	 tfvn                	 INTEGER  (0)
,	 	 	 scid                	 INTEGER  (0 .. 255)
,	 	 	 vcid                	 INTEGER  (0 .. 63)
	 	 }

}



-- This event notifies any change of the tmAosVcDemuxResourceStat parameter.
tmAosVcDemuxResourceStatChangeEventOid	 OBJECT IDENTIFIER ::= { 1 3 112 4 4 2 1 40501 2 1 1 }




-- The event value reports the tmAosVcDemuxResourceStat value that applies since the
--  notified tmAosVcDemuxResourceStatChange event occurred.
tmAosVcDemuxResourceStatChangeEventValueValueOid	 OBJECT IDENTIFIER ::= { 1 3 112 4 4 2 1 40501 2 1 1 1 }

TmAosVcDemuxResourceStatChangeEventValue	 ::= TmAosVcDemuxResourceStat


-- This directive permits setting of the controllable parameters of the TmAosVcDemux
--  FR type. 
tmAosVcDemuxSetContrParamsDirectiveOid	 OBJECT IDENTIFIER ::= { 1 3 112 4 4 2 1 40501 3 1 1 }




-- The directive qualifier specifies the FR instance the directive shall act on and
--  contains a set of parameter identifier and parameter value pairs. To be valid, the
--  parameter identifier must reference a controllable parameter of the TmAosVcDemux
--  FR and the parameter value must be of the same type as the parameter value that
--  shall be set.
-- 
tmAosVcDemuxContrParamIdsAndValuesQualifierOid	 OBJECT IDENTIFIER ::= { 1 3 112 4 4 2 1 40501 3 1 1 1 }

TmAosVcDemuxContrParamIdsAndValues	 ::= DirectiveQualifier


-- none
tmAosPktExtractDeencapFrOid	 OBJECT IDENTIFIER ::= { 1 3 112 4 4 2 1 40502 }




-- This parameter reports the set of APIDs of the space packets that are to be forwarded
--  by means of Packet.indication primitives to the Return File Service Production FR.
--   If the APID set contains an element set to the value -1, no space packets shall
--  be forwarded to the Return File Service Production FR. 
tmAosSpacePktApidSetParamOid	 OBJECT IDENTIFIER ::= { 1 3 112 4 4 2 1 40502 1 1 1 1 }

TmAosSpacePktApidSet	 ::= NULL


-- The Frame Data Sink FR filters the stream of received annotated transfer frames from
--  a physical channel for subsequent recording in an instance of the Offline Frame
--  Buffer (classifier OfflineFrameBuffer). The purpose of this FR is to accommodate
--  data capture policies of Agencies that  pre-determine which subset of all received
--  frames are recorded for subsequent off-line retrieval. Each instance of the Frame
--  Data Sink is tied to (and scheduled as part of) a specific Space Link Session Service
--  Package, whereas the Offline Frame Buffer persists across the execution of multiple
--  SLS Service Packages.
frameDataSinkFrOid	 OBJECT IDENTIFIER ::= { 1 3 112 4 4 2 1 50100 }




-- This enumerated parameter reports the FrameDataSink FR resource status and can take
--  on four values:
-- -  - 'configured': the associated equipment has been configured
-- 
--     - 'operational': the associated equipment is active;
--     - 'interrupted': a
--  failure has been detected;
--     - 'halted': the associated equipment has been taken
--  out of service.
frameDataSinkResourceStatParamOid	 OBJECT IDENTIFIER ::= { 1 3 112 4 4 2 1 50100 1 1 1 1 }

FrameDataSinkResourceStat	 ::= ResourceStat


-- This parameter configures and reports the section of received annotated transfer
--  frames to be stored in the associated Offline Frame Buffer instance. The values
--  are:
--  - 'all': which specifies that all annotated frames from the received physical
--  channel are to be recorded, or
--  - "channelList';  which specifies the set of master
--  channels and/or virtual channels that are to be stored. The valid values are specfic
--  to the space data link protocol - TM, AOS, or USLP. The channel list is specified
--  as a SEQUENCE OF SCIDs, each of which contains either 'all' (indicating aht all
--  VCs of the master channel are to be stored) or the SEQUENCE OF VCIDs that are to
--  be stored. The ranges of the SCID and VCID fields are limited to the selected space
--  data link protocol.
frameDataSinkStorageSelectionParamOid	 OBJECT IDENTIFIER ::= { 1 3 112 4 4 2 1 50100 1 2 1 1 }

FrameDataSinkStorageSelection	 ::= CHOICE
{
	 all                 	 [0]	 	 NULL
,	 channelList         	 [1]	 	 CHOICE
	 {

	 	 -- TFVN ='00' binary for TM master channels
	 	 tM                  	 [0]	 	 SEQUENCE  (SIZE( 1 .. 1024))  OF	 SEQUENCE
	 	 	 {
	 	 	 	 tmScid              	 INTEGER  (0 .. 1023)
,	 	 	 	 tmVcSelection       	 CHOICE
	 	 	 	 {
	 	 	 	 	 allTmVcids          	 [0]	 	 NULL
,	 	 	 	 	 selectedTmVcids     	 [1]	 	 SEQUENCE  (SIZE( 1 .. 8))  OF	 INTEGER  (0 .. 7)
	 	 	 	 }

	 	 	 }

,
	 	 -- TFVN = '01' binary for AOS master channels
	 	 aos                 	 [1]	 	 SEQUENCE  (SIZE( 1 .. 256))  OF	 SEQUENCE
	 	 	 {
	 	 	 	 aosScid             	 INTEGER  (0 .. 255)
,	 	 	 	 aosVcSelection      	 CHOICE
	 	 	 	 {
	 	 	 	 	 allAosVcids         	 [0]	 	 NULL
,	 	 	 	 	 selectedAosVcids    	 [1]	 	 SEQUENCE  (SIZE( 1 .. 64))  OF	 INTEGER  (0 .. 63)
	 	 	 	 }

	 	 	 }

,
	 	 -- TFVN = '1100' binary for USLP master channels
	 	 uslp                	 [2]	 	 SEQUENCE  (SIZE( 1 .. 65536))  OF	 SEQUENCE
	 	 	 {
	 	 	 	 uslpScid            	 INTEGER  (0 .. 65535)
,	 	 	 	 uslpVcSelection     	 CHOICE
	 	 	 	 {
	 	 	 	 	 allUslpVcids        	 [0]	 	 NULL
,	 	 	 	 	 selectedUslpVcids   	 [1]	 	 SEQUENCE  (SIZE( 1 .. 64))  OF	 INTEGER  (0 .. 63)
	 	 	 	 }

	 	 	 }

	 }

}



-- This event notifies any change of the frameDataSinkResourceStat.
frameDataSinkResourceStatChangeEventOid	 OBJECT IDENTIFIER ::= { 1 3 112 4 4 2 1 50100 2 1 1 }




-- The event value reports the frameDataSinkResourceStat value that applies after the
--  resource status of  the frameDataSink resource status has changed.
frameDataSinkResourceStatChangeValueValueOid	 OBJECT IDENTIFIER ::= { 1 3 112 4 4 2 1 50100 2 1 1 1 }

FrameDataSinkResourceStatChangeValue	 ::= FrameDataSinkResourceStat


-- This directive sets the controllable parameters of the FrameDataSink FR type.
frameDataSinkSetContrParamsDirectiveOid	 OBJECT IDENTIFIER ::= { 1 3 112 4 4 2 1 50100 3 1 1 }




-- The directive qualifier specifies the FR instance the directive shall act on and
--  contains a set of parameter identifier and parameter value pairs. To be valid, the
--  parameter identifier must reference a controllable parameter of the Frame Data Sink
--  FR and the parameter value must be of the same type as the parameter value that
--  shall be set. 
frameDataSinkContrParamIdsAndValuesQualifierOid	 OBJECT IDENTIFIER ::= { 1 3 112 4 4 2 1 50100 3 1 1 1 }

FrameDataSinkContrParamIdsAndValues	 ::= DirectiveQualifier


-- The local CFDP entity represents a local CFDP entity being able to communicate with
--  remote entities.
cfdpEntityFrOid	 OBJECT IDENTIFIER ::= { 1 3 112 4 4 2 1 50200 }




-- This enumerated parameter reports the overall status of the CFDP entity and can take
--  on four values: 
-- - 'configured': The CFDP entity has been configured but has not
--  been enabled for operations; 
--  - 'operational': The CFDP entity is able to carry
--  out operations; 
--  - 'interrupted': a failure has been detected that prevents the
--  CFDP entity form functioning nominally; 
--  - 'halted' The operator has set the entity
--  to 'halted'. That implies that all on-going transactions are suspended. 
cfdpLocalEntityResourceStatParamOid	 OBJECT IDENTIFIER ::= { 1 3 112 4 4 2 1 50200 1 1 1 1 }

CfdpLocalEntityResourceStat	 ::= ResourceStat


-- This parameter configures and reports the entity ID of the local CFDP entity.
cfdpLocalEntityIdParamOid	 OBJECT IDENTIFIER ::= { 1 3 112 4 4 2 1 50200 1 2 1 1 }

CfdpLocalEntityId   	 ::= CfdpEntityId


-- The CFDP remote entity configuration parameter reports on the remote CFDP entities
--  known to this local CFDP entity.
cfdpRemoteEntityConfigurationParamOid	 OBJECT IDENTIFIER ::= { 1 3 112 4 4 2 1 50200 1 3 1 1 }

CfdpRemoteEntityConfiguration	 ::= SEQUENCE  OF	 SEQUENCE
	 {
	 	 cfdpRemoteEntityId  	 CfdpEntityId
,
	 	 -- UT Address to use when transmitting to this entity.
	 	 cfdpRemoteUtAddress 	 VisibleString
,
	 	 -- For use in computing NAK and positive ACK timer intervals.
	 	 cfdpRemoteOneWayLightTime	 INTEGER  (0 .. 4294967295)
,
	 	 -- For use in computing NAK and positive ACK timer intervals.
	 	 cfdpRemoteTotalRoundTripAllowanceForQueuingDelay	 INTEGER  (0 .. 4294967295)
,
	 	 -- Asynchronous NAK interval in seconds
	 	 cfdpRemoteAsynchronousNakInterval	 CfdpOptionalTimer
,
	 	 -- Asynchronous Keep Alive interval in seconds
	 	 cfdpRemoteAsynchronousKeepAliveInterval	 CfdpOptionalTimer
,
	 	 -- This element reports on the report timer period in seconds at which the remote CFDP
	 	 --  entity will issue report.indication primitives. If the value of the parameter is
	 	 --  zero, the remote entity does not to issue report.indication primitives periodically.
	 	 cfdpRemoteAsynchronousReportInterval	 CfdpOptionalTimer
,
	 	 -- True or false.
	 	 cfdpRemoteImmediateNakModeEnabled	 TcLinkStat
,
	 	 -- Expressed as a time interval in seconds, or N/A.
	 	 cfdpRemotePromptTransmissionInterval	 CfdpOptionalTimer
,
	 	 -- This element reports if the Default transmission mode is Acknowledged or unacknowledged.
	 	 cfdpRemoteDefaultTransmissionMode	 CfdpTransmissionModeType
,
	 	 -- Disposition of incomplete received file on transaction cancellation
	 	 cfdpRemoteDispositionOfIncompleteReceivedFile	 ENUMERATED
	 	 {
	 	 	 discard             	 	 (0)
	 	 ,	 retain              	 	 (1)
	 	 }

,
	 	 -- This element reports if at the remote CFDP entity the CRC option is active.
	 	 cfdpRemoteCrcRequiredOnTransmission	 TcLinkStat
,
	 	 -- This element reports on the maximum file segment length (in octets) the remote CFDP
	 	 --  entities are able to handle.
	 	 cfdpRemoteMaximumFileSegmentLength	 INTEGER 
,
	 	 -- Expressed as a number of octets, or N/A.
	 	 cfdpRemoteKeepAliveDiscrepancyLimit	 CHOICE
	 	 {
	 	 	 keepAliveDiscrepancyLimit	 [0]	 	 INTEGER  (0 .. 4294967295)
,	 	 	 notApplicable       	 [1]	 	 NULL
	 	 }

,
	 	 -- Number of expirations.
	 	 cfdpRemotePositiveAckTimerExpirationLimit 	 INTEGER 
,
	 	 -- Number of expirations.
	 	 cfdpRemoteNakTimerExpirationLimit	 INTEGER 
,
	 	 -- Maximum period in seconds that may pass without reception of a PDU until the remote
	 	 --  CFDP entity will declare an Inactivity Fault condition. 
	 	 cfdpRemoteTransactionInactivityLimit	 CfdpTimer
,
	 	 -- Start/End of transmission opportunity A signal produced by the operating environment.
	 	 cfdpRemoteTransmissionWindow	 ENUMERATED
	 	 {
	 	 	 open                	 	 (0)
	 	 ,	 closed              	 	 (1)
	 	 }

,
	 	 -- Start/End of reception opportunity. A signal produced by the operating environment.
	 	 cfdpRemoteReceptionWindow	 ENUMERATED
	 	 {
	 	 	 open                	 	 (0)
	 	 ,	 closed              	 	 (1)
	 	 }

	 }



-- This parameter provides the configuration of the local CFDP entity as per CCSDS 727.0-B-4:
-- 
-- -
--  Local Entity ID
-- 
-- - EOF-Sent.indication required				True or false.
-- 
-- - EOF-Recv.indication						True
--  or false.
-- 
-- - File-Segment-Recv.indication required		True or false.
-- Transaction-Finished.indication
-- required
--  when acting as receiving entity		True or false.
-- 
-- - Suspended.indication required
--  when
-- acting as receiving entity					True or false.
-- 
-- - Resumed.indication required
--  when acting
-- as receiving entity							True or false.
-- 
-- - Default fault handlers For
--  each type of fault condition,
--  a default handler
-- 
-- - Routing information (Extended
--  procedures
-- only) For each entity in the system, a list of all
-- adjacent entities.
-- 
cfdpLocalEntityConfigurationParamOid	 OBJECT IDENTIFIER ::= { 1 3 112 4 4 2 1 50200 1 4 1 1 }

CfdpLocalEntityConfiguration	 ::= SEQUENCE
{

	 -- This element reports if the local CFDP entity is configured to provide an EOF-sent.indication
	 --  to the FwdFileServer FR when the initial transmission of the transaction's EOF PDU
	 --  has been performed. It can take on two values:
	 -- - true: EOF-sent indication enabled;
	 -- -
	 --  false: EOF-sent indication disabled.
	 cfdpLocalEofSentIndicationRequired	 TcLinkStat
,
	 -- This element reports if the local CFDP entity is configured to provide a File-Segment-Recv.indication
	 --  to the RtnFileServer FR when individual file data segments have been received from
	 --  the sending end. It can take on two values:
	 -- - true: File-Segment-Recv indication
	 --  enabled;
	 -- - false: File-Segment-Recv indication disabled.
	 cfdpLocalRecvIndicationRequired	 TcLinkStat
,
	 -- This element reports if the local CFDP entity is configured to provide a File-Segment-Recv.indication
	 --  to the RtnFileServer FR when individual file data segments have been received from
	 --  the sending end. It can take on two values:
	 -- - true: File-Segment-Recv indication
	 --  enabled;
	 -- - false: File-Segment-Recv indication disabled.
	 cfdpLocalFileSegmentRecvdIndicationRequired	 TcLinkStat
,
	 -- This element reports if the local CFDP entity is configured to provide a Transaction-Finished.indication
	 --  to the RtnFileServer FR when the transaction is complete. It can take on two values:
	 -- -
	 --  true: Transaction-Finished indication enabled;
	 -- - false: 	Transaction-Finished indication
	 --  disabled.
	 cfdpLocalTransactionFinishedIndicationRequired	 TcLinkStat
,
	 -- This element reports if the local CFDP entity is configured to provide a Suspended.indication.
	 --  It can take on two values:
	 -- - true: indication enabled;
	 -- - false: indication disabled.
	 cfdpLocalSuspendedIndicationRequired	 TcLinkStat
,
	 -- This element reports if the local CFDP entity is required to provide resume indications.
	 --  It can take on two values:
	 -- - true: indication enabled;
	 -- - false: indication disabled.
	 -- 
	 cfdpLocalResumedIndicationRequired	 TcLinkStat
,
	 -- Provides the setting of the fault handler when the positive ack limit is reached.
	 --  
	 cfdpLocalPositiveAckLimitReachedFaultHandler	 CfdpFaultHandler
,
	 -- Provides the setting of the fault handler when the keep alive lmit is reached.
	 cfdpLocalKeepAliveLimitFaultHandler	 CfdpFaultHandler
,
	 -- Provides the setting of the fault handler when invalid trnasmission mode is encountered.
	 cfdpLocalInvalidTransmissionModeFaultHandler	 CfdpFaultHandler
,
	 -- Provides the setting of the fault handler when the receiving CFDP entity determines
	 --  that the filestore cannot accept the file. 
	 cfdpLocalFilestoreRejectionFaultHandler	 CfdpFaultHandler
,
	 -- Provides the setting of the fault handler when the a Checksum Failure is encounterd.
	 --  A Checksum Failure fault shall be declared if the compared checksums are not
	 -- equal.
	 cfdpLocalFileChecksumFailureFaultHandler	 CfdpFaultHandler
,
	 -- Provides the setting of the fault handler when a file size error is encountered.
	 -- Upon
	 --  initial receipt of the EOF (No error) PDU, the file size indicated in the
	 -- PDU shall
	 --  be compared to the transaction reception progress and a File Size Error fault
	 -- declared
	 --  if the progress exceeds the file size.
	 cfdpLocalFileSizeErrorFaultHandler	 CfdpFaultHandler
,
	 -- Provides the setting of the fault handler when the NAK limit is reached.
	 cfdpLocalNakLimitReachedFaultHandler	 CfdpFaultHandler
,
	 -- Provides the setting of the fault handler when the inactivity limit is detected for
	 --  a transaction.
	 cfdpLocalInactivityDetectedFaultHandler	 CfdpFaultHandler
,
	 -- Provides the setting of the fault handler if the segmentation control service parameter
	 --  has requested that record boundaries be respected and there is no observable record
	 --  structure to the file. 
	 cfdpLocalInvalidFileStructureFaultHandler	 CfdpFaultHandler
,
	 -- Provides the setting of the fault handler if Check timer expiration limit has been
	 --  reached and a Check Limit Reached fault has been declared. 
	 cfdpLocalCheckLimitReachedFaultHandler	 CfdpFaultHandler
,
	 -- This element denotes for each CFDP entity in the system, a list of alladjacent CFDP
	 --  entities.
	 cfdpLocalRoutingInformation	 SEQUENCE  OF	 INTEGER 
}



-- The Transaction.indication primitive shall be used to indicate the Transaction identifier
-- to
--  the source CFDP user.
cfdpTransactionIndicationEventOid	 OBJECT IDENTIFIER ::= { 1 3 112 4 4 2 1 50200 2 1 1 }




-- The transaction ID parameter shall uniquely identify a single instance of FDU
-- delivery
--  and shall contain the ID of the source CFDP entity together with a sequence number
-- that
--  is specific to that entity.
-- 
-- NOTE
-- 1: At any moment, any given transaction ID is
--  unique within the CFDP addressing
-- domain that encompasses the source CFDP entity.
-- 
-- NOTE
--  2: The entity ID and transaction sequence number are variable in length to
-- accommodate
--  differing mission requirements. A common parsing scheme is defined
-- to allow full
--  interoperability despite differing parameter lengths.
cfdpTransactionTransactionIdValueOid	 OBJECT IDENTIFIER ::= { 1 3 112 4 4 2 1 50200 2 1 1 1 }

CfdpTransactionTransactionId	 ::= CfdpTransactionIdType


-- The EOF-Sent.indication primitive shall be used to notify the source CFDP user of
--  the
-- initial transmission of a transaction’s EOF PDU.
cfdpEofSentIndicationEventOid	 OBJECT IDENTIFIER ::= { 1 3 112 4 4 2 1 50200 2 2 1 }




-- The transaction ID parameter shall uniquely identify a single instance of FDU
-- delivery
--  and shall contain the ID of the source CFDP entity together with a sequence number
-- that
--  is specific to that entity.
-- 
-- NOTE
-- 1: At any moment, any given transaction ID is
--  unique within the CFDP addressing
-- domain that encompasses the source CFDP entity.
-- 
-- NOTE
--  2: The entity ID and transaction sequence number are variable in length to
-- accommodate
--  differing mission requirements. A common parsing scheme is defined
-- to allow full
--  interoperability despite differing parameter lengths.
cfdpEofSentTransactionIdValueOid	 OBJECT IDENTIFIER ::= { 1 3 112 4 4 2 1 50200 2 2 1 1 }

CfdpEofSentTransactionId	 ::= CfdpTransactionIdType


-- The Transaction-Finished.indication primitive shall be used to indicate to the source
-- or
--  destination CFDP user that the transaction is complete and that the source CFDP
--  user is
-- authorized to modify or delete any retransmission buffer (file) that it
--  was sharing with the
-- protocol entity to conserve persistent storage space.
cfdpTransactionFinishedIndicationEventOid	 OBJECT IDENTIFIER ::= { 1 3 112 4 4 2 1 50200 2 3 1 }




-- Indicates a finshied transaction. The following informaiton is provided as per CFDP
--  blue book:
-- - transaction ID;
-- - filestore responses;
-- - condition code;
-- - file
--  status;
-- - delivery code.
cfdpFinishedTransactionValueOid	 OBJECT IDENTIFIER ::= { 1 3 112 4 4 2 1 50200 2 3 1 1 }

CfdpFinishedTransaction	 ::= SEQUENCE
{
	 transactionId       	 [0]	 	 CfdpTransactionIdType
,	 fileStoreResponses  	 [1]	 	 SEQUENCE
	 {
	 	 actionCode          	 [0]	 	 CfdpActionCode
,	 	 statusCode          	 [1]	 	 CfdpActionCode
,	 	 firstFileName       	 [2]	 	 VisibleString
,	 	 secondFileName      	 [3]	 	 VisibleString OPTIONAL
,	 	 fileStoreMessage    	 [4]	 	 VisibleString OPTIONAL
	 }
 OPTIONAL
,	 statusReport        	 [2]	 	 VisibleString OPTIONAL
,	 conditionCode       	 [3]	 	 CfdpConditionCodeType
,	 fileStatus          	 [4]	 	 ENUMERATED
	 {
	 	 deliveredFileDiscardedDeliberately	 	 (0)
	 ,	 deliveredFileDiscardedDueToFilestoreRejection	 	 (1)
	 ,	 deliveredFileRetainedInFilestoreSuccessfully	 	 (2)
	 ,	 deliveredFileStatusUnreported	 	 (3)
	 }

,	 deliveryCode        	 [5]	 	 ENUMERATED
	 {
	 	 dataComplete        	 	 (0)
	 ,	 dataIncomplete      	 	 (1)
	 }

}



-- The Metadata-Recv.indication primitive shall be used to indicate to the destination
-- CFDP
--  user that the metadata associated with a transaction has been received.
cfdpMetadataRcvdIndicationEventOid	 OBJECT IDENTIFIER ::= { 1 3 112 4 4 2 1 50200 2 4 1 }




-- The following metadata information is provided:
-- - transaction ID;
-- - source CFDP
--  entity ID;
-- - source file name;
-- - destination file name;
-- - messages to user.	
cfdpMetadataIndicationValueOid	 OBJECT IDENTIFIER ::= { 1 3 112 4 4 2 1 50200 2 4 1 1 }

CfdpMetadataIndication	 ::= SEQUENCE
{
	 transactionId       	 [0]	 	 CfdpTransactionIdType
,
	 -- CFDP Source Entity ID
	 sourceEntityId      	 [1]	 	 CfdpEntityId
,	 sourceFileName      	 [2]	 	 VisibleString OPTIONAL
,	 destinationFileName 	 [3]	 	 VisibleString OPTIONAL
,	 messagesToUser      	 [4]	 	 VisibleString OPTIONAL
}



-- The File-Segment-Recv.indication primitive shall be used to indicate, to the destination
-- CFDP
--  user, the receipt of individual file data (non metadata) segments.
cfdpFileSegmentRcvdIndicationEventOid	 OBJECT IDENTIFIER ::= { 1 3 112 4 4 2 1 50200 2 5 1 }




-- The following information is provided for a File Segment Received Indication:
-- -
--  transaction ID;
-- - offset;
-- - length.
cfdpFileSegmentIndicationValueValueOid	 OBJECT IDENTIFIER ::= { 1 3 112 4 4 2 1 50200 2 5 1 1 }

CfdpFileSegmentIndicationValue	 ::= SEQUENCE
{
	 transactionId       	 CfdpTransactionIdType
,	 offset              	 INTEGER  (0 .. 18446744073709551615)
,	 segmentLength       	 INTEGER  (0 .. 65535)
}



-- The Report.indication primitive shall be used to report to the CFDP user on the status
--  of
-- a transaction.
cfdpReportRcvdIndicationEventOid	 OBJECT IDENTIFIER ::= { 1 3 112 4 4 2 1 50200 2 6 1 }




-- The following information is provided for a Report Received Indication:
-- - transaction
--  ID;
-- - status report.
cfdpReportIndicationValueOid	 OBJECT IDENTIFIER ::= { 1 3 112 4 4 2 1 50200 2 6 1 1 }

CfdpReportIndication	 ::= SEQUENCE
{
	 transactionId       	 CfdpTransactionIdType
,
	 -- The format and scope of the status report parameter are specific to the implementation.
	 statusReport        	 VisibleString
}



-- The Suspended.indication primitive shall be used to indicate to the CFDP user that
--  the
-- transaction has been suspended.
cfdpSuspendedIndicationEventOid	 OBJECT IDENTIFIER ::= { 1 3 112 4 4 2 1 50200 2 7 1 }




-- The following inforamtion is provided for a Suspended Indication:
-- - transaction
--  ID;
-- - condition code.
-- 
cfdpSuspendedIndicationValueOid	 OBJECT IDENTIFIER ::= { 1 3 112 4 4 2 1 50200 2 7 1 1 }

CfdpSuspendedIndication	 ::= SEQUENCE
{
	 transactionId       	 CfdpTransactionIdType
,	 conditionCode       	 CfdpConditionCodeType
}



-- The Resumed.indication primitive shall be used to indicate to the CFDP user that
--  the
-- transaction has been resumed.
cfdpResumedIndicationEventOid	 OBJECT IDENTIFIER ::= { 1 3 112 4 4 2 1 50200 2 8 1 }




-- The following information is provided for a Resumed Indication:
-- - transaction ID;
-- -
--  progress.
cfdpResumedIndicationValueOid	 OBJECT IDENTIFIER ::= { 1 3 112 4 4 2 1 50200 2 8 1 1 }

CfdpResumedIndication	 ::= SEQUENCE
{
	 transactionId       	 CfdpTransactionIdType
,
	 -- Progress indicates how far the issuing CFDP entity had progressed
	 progress            	 INTEGER  (0 .. 18446744073709551615)
}



-- The Fault.indication primitive shall be used to indicate to the CFDP user the occurrence
-- of
--  a fault condition for which the designated fault handler was ‘Ignore’.
cfdpFaultIndicationEventOid	 OBJECT IDENTIFIER ::= { 1 3 112 4 4 2 1 50200 2 9 1 }




-- For a fault indication the following information is provided:
-- - transaction ID;
-- -
--  condition code;
-- - progress.
cfdpFaultIndicationValueOid	 OBJECT IDENTIFIER ::= { 1 3 112 4 4 2 1 50200 2 9 1 1 }

CfdpFaultIndication 	 ::= CfdpFaultOrAbandonedIndicationType


-- The Abandoned.indication primitive shall be used to indicate to the CFDP user the
-- occurrence
--  of a fault condition for which the designated fault handler was ‘Abandon’.
cfdpAbandonedIndicationEventOid	 OBJECT IDENTIFIER ::= { 1 3 112 4 4 2 1 50200 2 10 1 }




-- For an Abandoned indication the following information is provided:
-- - transaction
--  ID;
-- - condition code;
-- - progress.
cfdpAbandonedIndicationValueOid	 OBJECT IDENTIFIER ::= { 1 3 112 4 4 2 1 50200 2 10 1 1 }

CfdpAbandonedIndication	 ::= CfdpFaultOrAbandonedIndicationType


-- The EOF-Recv.indication primitive shall be used to indicate to the destination CFDP
--  user
-- that the EOF PDU associated with a transaction has been received.
cfdpEofRcvdIndicationEventOid	 OBJECT IDENTIFIER ::= { 1 3 112 4 4 2 1 50200 2 11 1 }




-- The transaction ID for which EOF is indicated.
cfdpEofRcvdTransactionIdValueOid	 OBJECT IDENTIFIER ::= { 1 3 112 4 4 2 1 50200 2 11 1 1 }

CfdpEofRcvdTransactionId	 ::= CfdpTransactionIdType


-- When (and only when) the Extended procedures are in operation, the Transfer-
-- Consigned.indication
--  primitive shall be used to indicate, to the source CFDP user, the
-- complete reception
--  of a file by the first waypoint.
cfdpTransferConsignedIndicationEventOid	 OBJECT IDENTIFIER ::= { 1 3 112 4 4 2 1 50200 2 12 1 }




-- The transaction ID for which Consigned Indication is provided.
cfdpConsignedTransactionIdValueOid	 OBJECT IDENTIFIER ::= { 1 3 112 4 4 2 1 50200 2 12 1 1 }

CfdpConsignedTransactionId	 ::= CfdpTransactionIdType


-- The Put.request primitive shall be used by the application to request delivery of
--  a file from the source filestore to a destination filestore.
cfdpPutRequestDirectiveOid	 OBJECT IDENTIFIER ::= { 1 3 112 4 4 2 1 50200 3 1 1 }




-- The Put Request Qualifier provides
-- - destination CFDP entity ID;
-- - source file
--  name;		
-- - destination file name;
-- - segmentation control;
-- - fault handler overrrides;
-- -
--  flow label; 				
-- - transmission mode;		
-- - messages to user;		
-- - filestore requests.
cfdpPutRequestQualifierOid	 OBJECT IDENTIFIER ::= { 1 3 112 4 4 2 1 50200 3 1 1 1 }

CfdpPutRequest      	 ::= SEQUENCE
{

	 -- The destination CFDP entity ID parameter shall uniquely identify the CFDP entity
	 --  to
	 -- which the FDU is to be sent.
	 destEntityId        	 [0]	 	 CfdpEntityId
,	 sourceFileName      	 [1]	 	 VisibleString OPTIONAL
,	 destinationFileName 	 [2]	 	 VisibleString OPTIONAL
,
	 -- The segmentation control parameter
	 -- a) shall indicate whether the file being delivered
	 --  is to be segmented as an array of octets
	 -- or as an array of variable-length records;
	 -- b)
	 --  shall be omitted when local and remote file names are omitted.
	 segmentationControl 	 [3]	 	 ENUMERATED
	 {
	 	 recordBoundariesRespected	 	 (0)
	 ,	 recordBoundariesNotRespected	 	 (1)
	 }
 OPTIONAL
,	 faultHandlerOverrides	 [4]	 	 SEQUENCE  OF	 SEQUENCE
	 	 {
	 	 	 faultCondition      	 CfdpConditionCodeType
,	 	 	 action              	 CfdpFaultHandler
	 	 }
 OPTIONAL
,	 flowLabel           	 [5]	 	 OCTET STRING OPTIONAL
,	 transmissionMode    	 [6]	 	 CfdpTransmissionModeType OPTIONAL
,	 messagesToUser      	 [7]	 	 VisibleString OPTIONAL
,	 filestoreRequests   	 [8]	 	 SEQUENCE  OF	 SEQUENCE
	 	 {
	 	 	 action              	 CfdpActionCode
,	 	 	 fileNameOne         	 VisibleString
,	 	 	 fileNameTwo         	 VisibleString OPTIONAL
	 	 }
 OPTIONAL
}



-- The Report.request primitive shall be used to request a report on the status of a
-- transaction.
cfdpReportRequestDirectiveOid	 OBJECT IDENTIFIER ::= { 1 3 112 4 4 2 1 50200 3 2 1 }




-- The transaction ID for which a report is requested.
cfdpReportRequestTransactionIdQualifierOid	 OBJECT IDENTIFIER ::= { 1 3 112 4 4 2 1 50200 3 2 1 1 }

CfdpReportRequestTransactionId	 ::= CfdpTransactionIdType


-- The Cancel.request primitive shall be used to request that a transaction be canceled.
cfdpCancelRequestDirectiveOid	 OBJECT IDENTIFIER ::= { 1 3 112 4 4 2 1 50200 3 3 1 }




-- The transaction ID for which cancellation is requested.
cfdpCancelRequestTransactionIdQualifierOid	 OBJECT IDENTIFIER ::= { 1 3 112 4 4 2 1 50200 3 3 1 1 }

CfdpCancelRequestTransactionId	 ::= CfdpTransactionIdType


-- The Suspend.request primitive shall be used to request that a transaction be suspended.
cfdpSuspendRequestDirectiveOid	 OBJECT IDENTIFIER ::= { 1 3 112 4 4 2 1 50200 3 4 1 }




-- The transaction ID for which cancellation is requested.
cfdpSuspendTransactionIdQualifierOid	 OBJECT IDENTIFIER ::= { 1 3 112 4 4 2 1 50200 3 4 1 1 }

CfdpSuspendTransactionId	 ::= CfdpTransactionIdType


-- The Resume.request primitive shall be used to request that a suspended transaction
--  be
-- resumed.
cfdpResumeRequestDirectiveOid	 OBJECT IDENTIFIER ::= { 1 3 112 4 4 2 1 50200 3 5 1 }




-- The Transaction ID for which cancellation is requested.
cfdpResumeTransactionIdQualifierOid	 OBJECT IDENTIFIER ::= { 1 3 112 4 4 2 1 50200 3 5 1 1 }

CfdpResumeTransactionId	 ::= CfdpTransactionIdType


-- none
fwdFileSvcProdFrOid	 OBJECT IDENTIFIER ::= { 1 3 112 4 4 2 1 50201 }




-- none
rtnFileSvcProdFrOid	 OBJECT IDENTIFIER ::= { 1 3 112 4 4 2 1 50202 }




-- none
cfdpSendEntityFrOid	 OBJECT IDENTIFIER ::= { 1 3 112 4 4 2 1 999900 }




-- none
cfdpRcvEntityFrOid	 OBJECT IDENTIFIER ::= { 1 3 112 4 4 2 1 999100 }




-- TdmSegmentGen performs the production functions associated with collecting: angle
--  measurements from the antenna; receive frequency, carrier power, carrier power to
--  noise spectral density, and Doppler measurements from the return space link; range
--  and ranging power to noise spectral density measurements from the received space
--  links; and transmit frequency and transmit frequency rate from the transmitted space
--  link in order to generate Tracking Data Message (TDM) segments containing those
--  measurements.
tdmSegmentGenFrOid	 OBJECT IDENTIFIER ::= { 1 3 112 4 4 2 1 60100 }




-- This enumerated parameter reports the TdmSegmentGen resource status and can take
--  on four values:
--    - 'configured': the associated equipment has been configured
--  to ingest tracking data measurements and produce TDM atomic segments
--     - 'operational':
--  the associated equipment is ingesting tracking data measurements and produce TDM
--  atomic segments;
--     - 'interrupted': a failure has been detected;
--     - 'halted':
--  the associated equipment has been taken out of service.
tdmSegGenResourceStatParamOid	 OBJECT IDENTIFIER ::= { 1 3 112 4 4 2 1 60100 1 1 1 1 }

TdmSegGenResourceStat	 ::= ResponderPortId


-- This complex-valued parameter configures and reports the set of Carrier Power tracking
--  data paths for which Carrier Power Atomic Segments are to be generated during the
--  execution of the Service Package.
tdmSegGenCarrierPowerPathTableParamOid	 OBJECT IDENTIFIER ::= { 1 3 112 4 4 2 1 60100 1 2 1 1 }

TdmSegGenCarrierPowerPathTable	 ::= SEQUENCE  OF	 SEQUENCE
	 {

	 	 -- trackingDataPathId, apertureName, spaceUserNodeName,reportingPeriod, and frName
	 	 pathTableCommonElements	 TdmPathTableCommonElements
,
	 	 -- The frequency band of the carrier received from the Space user Node.
	 	 rcvFreqBand         	 FreqBands
	 }



-- This complex-valued parameter configures and reports the set of Pc/No tracking data
--  paths for which Pc/No Atomic Segments are to be generated during the execution of
--  the Service Package.
tdmSegGenPcOverN0PathTableParamOid	 OBJECT IDENTIFIER ::= { 1 3 112 4 4 2 1 60100 1 3 1 1 }

TdmSegGenPcOverN0PathTable	 ::= SEQUENCE  OF	 SEQUENCE
	 {

	 	 -- trackingDataPathId, apertureName, spaceUserNodeName,reportingPeriod, and frName
	 	 pathTableCommonElements	 TdmPathTableCommonElements
,
	 	 -- The frequency band of the carrier received from the Space user Node.
	 	 rcvFreqBand         	 FreqBands
	 }



-- This complex-valued parameter configures and reports the set of Pr/No tracking data
--  paths for which Pr/No Atomic Segments are to be generated during the execution of
--  the Service Package
tdmSegGenPrOverNoPathTableParamOid	 OBJECT IDENTIFIER ::= { 1 3 112 4 4 2 1 60100 1 4 1 1 }

TdmSegGenPrOverNoPathTable	 ::= SEQUENCE  OF	 SEQUENCE
	 {

	 	 -- trackingDataPathId, apertureName, spaceUserNodeName,reportingPeriod, and frName
	 	 pathTableCommonElements	 TdmPathTableCommonElements
,
	 	 -- The frequency band of the carrier received from the Space user Node.
	 	 rcvFreqBand         	 FreqBands
	 }



-- This complex-valued parameter configures and reports the set of Doppler (instantaneous)
--  tracking data paths for which Doppler (instantaneous) Atomic Segments are to be
--  generated during the execution of the Service Package.
tdmSegGenDoppInstPathTableParamOid	 OBJECT IDENTIFIER ::= { 1 3 112 4 4 2 1 60100 1 5 1 1 }

TdmSegGenDoppInstPathTable	 ::= SEQUENCE  OF	 SEQUENCE
	 {

	 	 -- trackingDataPathId, apertureName, spaceUserNodeName,reportingPeriod, and frName
	 	 pathTableCommonElements	 TdmPathTableCommonElements
,
	 	 -- The name of the receiving aperture, which that populates the PARTICIPANT_3 field
	 	 --  of the generated TDM segment. Used only if three-way Doppler measurements are taken
	 	 --  with both transmitting and receiving apertures at the same ESLT.
	 	 threeWayRcvAperture 	 VisibleString OPTIONAL
,
	 	 -- The frequency band of the carrier signal received from the Space User Node
	 	 rcvFreqBand         	 LabelListSetV1
,
	 	 -- The frequency band of the  carrier signal transmitted to the Space User Node. Not
	 	 --  used for 1-way Doppler.
	 	 xmitFreqBand        	 LabelListSetV1 OPTIONAL
	 }



-- This complex-valued parameter configures and reports the set of Doppler (integrated)
--  tracking data paths for which Doppler (integrated) Atomic Segments are to be generated
--  during the execution of the Service Package.
tdmSegGenDoppIntegPathTableParamOid	 OBJECT IDENTIFIER ::= { 1 3 112 4 4 2 1 60100 1 6 1 1 }

TdmSegGenDoppIntegPathTable	 ::= SEQUENCE  OF	 SEQUENCE
	 {

	 	 -- trackingDataPathId, apertureName, spaceUserNodeName,reportingPeriod, and frName
	 	 pathTableCommonElements	 TdmPathTableCommonElements
,
	 	 -- The name of the receiving aperture, which populates the PARTICIPANT_3 field of the
	 	 --  generated TDM segment. Used only if three-way Doppler measurements are taken with
	 	 --  both transmitting and receiving apertures at the same ESLT.
	 	 threeWayRcvAperture 	 VisibleString OPTIONAL
,
	 	 -- The frequency band of the carrier signal received from the Space User Node.
	 	 rcvFreqBand         	 FreqBands
,
	 	 -- The frequency band of the  carrier signal transmitted to the Space User Node. Not
	 	 --  used for 1-way Doppler.
	 	 xmitFreqBand        	 FreqBands OPTIONAL
,
	 	 -- The interval over which the Doppler measurements are to be integrated, in seconds.
	 	 integrationInterval 	 ShortIntUnsigned
,
	 	 -- The integration reference specifies whether the timetag represents the start, middle,
	 	 --  or end of the integration period.
	 	 integrationRef      	 ENUMERATED
	 	 {
	 	 	 start               	 	 (0)
	 	 ,	 middle              	 	 (1)
	 	 ,	 end                 	 	 (2)
	 	 }

	 }



-- This complex-valued parameter configures and reports the set of Range tracking data
--  paths for which Range Atomic Segments are to be generated during the execution of
--  the Service Package.
tdmSegGenRangePathTableParamOid	 OBJECT IDENTIFIER ::= { 1 3 112 4 4 2 1 60100 1 7 1 1 }

TdmSegGenRangePathTable	 ::= SEQUENCE  OF	 SEQUENCE
	 {

	 	 -- trackingDataPathId, apertureName, spaceUserNodeName,reportingPeriod, and frName
	 	 pathTableCommonElements	 TdmPathTableCommonElements
,
	 	 -- The name of the receiving aperture, which populates the PARTICIPANT_3 field of the
	 	 --  generated TDM segment. Used only if three-way Doppler measurements are taken with
	 	 --  both transmitting and receiving apertures at the same ESLT.
	 	 threeWayRcvAperture 	 VisibleString
,
	 	 -- The frequency band of the carrier signal received from the Space User Node.
	 	 rcvFreqBand         	 LabelListSetV1
,
	 	 -- The frequency band of the  carrier signal transmitted to the Space User Node.
	 	 xmitFreqBand        	 LabelListSetV1
,	 	 rangeUnits          	 ENUMERATED
	 	 {
	 	 	 km                  	 	 (0)
	 	 ,	 seconds             	 	 (1)
	 	 }

,
	 	 -- The interval over which the Range measurements are to be integrated, in seconds.
	 	 integrationInterval 	 ShortIntPos
,
	 	 -- he integration reference specifies whether the timetag represents the start, middle,
	 	 --  or end of the integration period.
	 	 integrationRef      	 ENUMERATED
	 	 {
	 	 	 start               	 	 (0)
	 	 ,	 middle              	 	 (1)
	 	 ,	 end                 	 	 (2)
	 	 }

	 }



-- This complex-valued parameter configures and reports the set of Receive Frequency
--  tracking data paths for which Receive Frequency Atomic Segments are to be generated
--  during the execution of the Service Package.
tdmSeqGenRcvFreqPathTableParamOid	 OBJECT IDENTIFIER ::= { 1 3 112 4 4 2 1 60100 1 8 1 1 }

TdmSeqGenRcvFreqPathTable	 ::= SEQUENCE  OF	 SEQUENCE
	 {

	 	 -- trackingDataPathId, apertureName, spaceUserNodeName,reportingPeriod, and frName
	 	 pathTableCommonElements	 TdmPathTableCommonElements
,
	 	 -- The frequency band of the carrier signal received from the Space User Node.
	 	 rcvFreqBand         	 FreqBands
	 }



-- This complex-valued parameter configures and reports the set of Transmit Frequency
--  tracking data paths for which Transmit Frequency Atomic Segments are to be generated
--  during the execution of the Service Package.
tdmSegGenXmitFreqPathTableParamOid	 OBJECT IDENTIFIER ::= { 1 3 112 4 4 2 1 60100 1 9 1 1 }

TdmSegGenXmitFreqPathTable	 ::= SEQUENCE  OF	 SEQUENCE
	 {

	 	 -- trackingDataPathId, apertureName, spaceUserNodeName,reportingPeriod, and frName
	 	 pathTableCommonElements	 TdmPathTableCommonElements
,
	 	 -- The frequency band of the  carrier signal transmitted to the Space User Node.
	 	 xmitFreqBand        	 FreqBands
	 }



-- This complex-valued parameter configures and reports the set of Transmit Frequency
--  Rate tracking data paths for which Transmit Frequency Rate Atomic Segments are to
--  be generated during the execution of the Service Package.
tdmSegGenXmitFreqRatePathTableParamOid	 OBJECT IDENTIFIER ::= { 1 3 112 4 4 2 1 60100 1 10 1 1 }

TdmSegGenXmitFreqRatePathTable	 ::= SEQUENCE  OF	 SEQUENCE
	 {

	 	 -- trackingDataPathId, apertureName, spaceUserNodeName,reportingPeriod, and frName
	 	 pathTableCommonElements	 TdmPathTableCommonElements
,
	 	 -- The frequency band of the  carrier signal transmitted to the Space User Node.
	 	 xmitFreqBand        	 FreqBands
	 }



-- This complex-valued parameter configures and reports the set of Antenna Angles tracking
--  data paths for which Antenna Angles Atomic Segments are to be generated during the
--  execution of the Service Package.
tdmSegGenAntAnglesPathTableParamOid	 OBJECT IDENTIFIER ::= { 1 3 112 4 4 2 1 60100 1 11 1 1 }

-- trackingDataPathId, apertureName, spaceUserNodeName,reportingPeriod, and frName
TdmSegGenAntAnglesPathTable	 ::= TdmPathTableCommonElements


-- This event notifies any change of the tdmSegGenResourceStat parameter.
tdmSegGenResourceStatChangeEventOid	 OBJECT IDENTIFIER ::= { 1 3 112 4 4 2 1 60100 2 1 1 }




-- The event value reports the tdmSegGenResourceStat value that applies since the notified
--  tdmSegGenResourceStatChange event occurred.
tdmSegGenResourceStatChangeValueValueOid	 OBJECT IDENTIFIER ::= { 1 3 112 4 4 2 1 60100 2 1 1 1 }

TdmSegGenResourceStatChangeValue	 ::= TdmSegGenResourceStat


-- This directive permits setting of the controllable parameters of the TdmSegmentGen
--  FR type. 
tdmSegGenSetContrParamsDirectiveOid	 OBJECT IDENTIFIER ::= { 1 3 112 4 4 2 1 60100 3 1 1 }




-- The directive qualifier specifies the FR instance the directive shall act on and
--  contains a set of parameter identifier and parameter value pairs. To be valid, the
--  parameter identifier must reference a controllable parameter of the TdmSegmentGen
--  FR and the parameter value must be of the same type as the parameter value that
--  shall be set.
tdmSegGenContrParamIdsAndValuesQualifierOid	 OBJECT IDENTIFIER ::= { 1 3 112 4 4 2 1 60100 3 1 1 1 }

TdmSegGenContrParamIdsAndValues	 ::= DirectiveQualifier


-- To be defined.
nonValRmDataCollectionFrOid	 OBJECT IDENTIFIER ::= { 1 3 112 4 4 2 1 60200 }




-- To be defined.
ddorRawDataCollectionFrOid	 OBJECT IDENTIFIER ::= { 1 3 112 4 4 2 1 60300 }




-- To be defined
openLoopRxFormatterFrOid	 OBJECT IDENTIFIER ::= { 1 3 112 4 4 2 1 60400 }




-- The Offline Frame Buffer is a repository of return transfer frames that are subsequently
--  retrieved by offline SLE transfer service instances that carry transfer frames or
--  space link data units that have been transferred across the space link within those
--  transfer frames.
-- 
-- The OfflineFrameBuffer FR corresponds to the Offline Frame Buffer
--  production entity defined in the SLE RAF and RCF Service Specification Recommended
--  Standards.
-- 
-- An instance of the OfflineFrameBuffer FR represents the allocation
--  of resources of a physical mass storage device to the Mission.
offlineFrameBufferFrOid	 OBJECT IDENTIFIER ::= { 1 3 112 4 4 2 1 70100 }




-- This enumerated parameter reports the OfflineFrameBuffer FR resource status and can
--  take on four values:
-- -  - 'configured': the associated equipment has been configured
-- 
--     - 'operational': the associated equipment is active;
--     - 'interrupted': a
--  failure has been detected;
--     - 'halted': the associated equipment has been taken
--  out of service.
offlineFrameBufferResourceStatParamOid	 OBJECT IDENTIFIER ::= { 1 3 112 4 4 2 1 70100 1 1 1 1 }

OfflineFrameBufferResourceStat	 ::= ResourceStat


-- This parameter reports the total storage (in megabytes) that has been allocated to
--  the Offline Frame Buffer instance. The allocation is made by the Provider Cross
--  Support Service System and is not reconfigurable by User Mission.
offlineFrameBufferAllocatedStorageParamOid	 OBJECT IDENTIFIER ::= { 1 3 112 4 4 2 1 70100 1 2 1 1 }

OfflineFrameBufferAllocatedStorage	 ::= LongIntPos


-- This parameter reports the total storage (in megabytes) that is currently available
--  in  the Offline Frame Buffer instance. The value increases when data are permanently
--  removed from the buffer and decreases when data are added to the buffer.
offlineFrameBufferAvailableStorageParamOid	 OBJECT IDENTIFIER ::= { 1 3 112 4 4 2 1 70100 1 3 1 1 }

OfflineFrameBufferAvailableStorage	 ::= LongIntUnsigned


-- This parameter reports the total storage (in megabytes) that is currently being used
--  in the Offline Frame Buffer instance. The value decreases when data are permanently
--  removed from the buffer and increases when data are added to the buffer.
offlineFrameBufferUsedStorageParamOid	 OBJECT IDENTIFIER ::= { 1 3 112 4 4 2 1 70100 1 4 1 1 }

OfflineFrameBufferUsedStorage	 ::= LongIntUnsigned


-- This parameter configures and reports the policy for retention of buffered frames.
--  The parameter has a choice of two values:
-- - 'never': all frames are retained unless
--  and until the used data storage reaches the allocated storage amount, at which point
--  frames are purged.
-- - 'timeLimited': the time period (in hours) between the time
--  of receipt of each frame and its automatic purge from the buffer.
-- 
-- Note - Data
--  may purged prior to the period specified by the timeLimited value if the data storage
--  usage reaches the allocated storage amount.
offlineFrameBufferDataRetentionPolicyParamOid	 OBJECT IDENTIFIER ::= { 1 3 112 4 4 2 1 70100 1 5 1 1 }

OfflineFrameBufferDataRetentionPolicy	 ::= CHOICE
{
	 never               	 [0]	 	 NULL
,	 timeLimited         	 [1]	 	 LongIntPos
}



-- This parameter configures and reports the priority by which frames are to be purged
--  when the allocated storage is reached. The parameter is the choice among two values:
-- 
--  - 'fifo': the first (oldest) frames stored are the first to be purged; or
--  - 'lifo':
--   the last (oldest) frames stored are the first to be purged;.
-- 
-- For each of these
--  choices, the ordered sequence of VCs for which frames are to be purged can be specified,
--  or "noVcPriority" can be selected to purge frames regardless of the VC to which
--  they belong.
-- 
offlineFrameBufferPurgePriorityParamOid	 OBJECT IDENTIFIER ::= { 1 3 112 4 4 2 1 70100 1 6 1 1 }

OfflineFrameBufferPurgePriority	 ::= SEQUENCE
{
	 firstOrLast         	 ENUMERATED
	 {
	 	 fifo                	 	 (0)
	 ,	 lifo                	 	 (1)
	 }

,	 gvcidPurgeOrder     	 CHOICE
	 {
	 	 noVcPriority        	 [0]	 	 NULL
,	 	 sequenceofGvcids    	 [1]	 	 SequenceOfGvcids
	 }

}



-- This parameter configures and reports the ratio (expressed as a percentage) of used
--  storage to allocated storage below which purging of the buffer is to cease.
offlineFrameBufferPurgeCessationThresholdParamOid	 OBJECT IDENTIFIER ::= { 1 3 112 4 4 2 1 70100 1 7 1 1 }

OfflineFrameBufferPurgeCessationThreshold	 ::= INTEGER  (1 .. 100)


-- This parameter configures and reports the ratio (expressed as a percentage) of used
--  storage to allocated storage at which the offlineFrameBufferPurgeWarning event is
--  emitted.
offlineFrameBufferPurgeWarningThresholdParamOid	 OBJECT IDENTIFIER ::= { 1 3 112 4 4 2 1 70100 1 8 1 1 }

OfflineFrameBufferPurgeWarningThreshold	 ::= INTEGER  (1 .. 100)


-- This event notifies any change of the offlineFrameBufferResourceStat.
offlineFrameBufferResourceStatChangeEventOid	 OBJECT IDENTIFIER ::= { 1 3 112 4 4 2 1 70100 2 1 1 }




-- The event value reports the offlineFrameBufferResourceStat value that applies after
--  the resource status of  the offlineFrameBuffer resource status has changed.
offlineFrameBufferResourceStatChangeValueValueOid	 OBJECT IDENTIFIER ::= { 1 3 112 4 4 2 1 70100 2 1 1 1 }

OfflineFrameBufferResourceStatChangeValue	 ::= OfflineFrameBufferResourceStat


-- This notifies that the ratio (expressed as a percentage) of used storage to allocated
--  storage ahas reached or exceeded the value specified by the offlineFrameBufferPurgeWarningThreshold
--  parameter. The value of the event reports the percentage if storage at the completion
--  of the purge.
offlineFrameBufferPurgeWarningEventOid	 OBJECT IDENTIFIER ::= { 1 3 112 4 4 2 1 70100 2 2 1 }




-- The value of the event reports the percentage if storage at the completion of the
--  purge.
offlineFrameBufferPurgeWarningValueValueOid	 OBJECT IDENTIFIER ::= { 1 3 112 4 4 2 1 70100 2 2 1 1 }

OfflineFrameBufferPurgeWarningValue	 ::= INTEGER  (1 .. 100)


-- This directive sets the controllable parameters of the OfflineFrameBuffer FR type.
offlineFrameBufferSetContrParamsDirectiveOid	 OBJECT IDENTIFIER ::= { 1 3 112 4 4 2 1 70100 3 1 1 }




-- The directive qualifier specifies the FR instance the directive shall act on and
--  contains a set of parameter identifier and parameter value pairs. To be valid, the
--  parameter identifier must reference a controllable parameter of the OfflineFrameBuffer
--  FR and the parameter value must be of the same type as the parameter value that
--  shall be set. 
offlineFrameBufferContrParamIdsAndValuesQualifierOid	 OBJECT IDENTIFIER ::= { 1 3 112 4 4 2 1 70100 3 1 1 1 }

OfflineFrameBufferContrParamIdsAndValues	 ::= DirectiveQualifier


-- The TDM Recording Buffer is a repository of tracking data segments that are subsequently
--  retrieved by Tracking Data CSTS Provider instances operating in the complete data
--  transfer mode. 
-- 
-- The TDM Recording Buffer FR corresponds to the Recording Buffer
--  production entity defined in annex F3 of the Cross Suppport Transfer Service - Tracking
--  Data Service Recommended Standard.
-- 
-- An instance of TdmRcrdBuffer records all TDM
--  Atomic Segments generated by the TsnSegGen FR instance with which it is associated.
--  A TdmRcrdBuffer instance makes available all TDM Atomic Segments that it retains
--  to any TdCstsProvider FR instance with which it is associated.
tdmRcrdBufferFrOid	 OBJECT IDENTIFIER ::= { 1 3 112 4 4 2 1 70200 }




-- This enumerated parameter reports the TdmRcrdBuffer FR resource status and can take
--  on four values:
-- -  - 'configured': the associated resource has been configured
-- 
--     - 'operational': the associated resource is active;
--     - 'interrupted': a failure
--  has been detected;
--     - 'halted': the associated resource has been taken out of
--  service.
-- 
-- NOTE - Because it is an offline data storage FR, the resource status
--  of the TdmRcrdBuffer FR is independent of any Service Package that it may be included
--  in. 
tdmRcrdBufferResourceStatParamOid	 OBJECT IDENTIFIER ::= { 1 3 112 4 4 2 1 70200 1 1 1 1 }

TdmRcrdBufferResourceStat	 ::= ResourceStat


-- This parameter configures and reports the maximum storage (in megabytes) allocated
--  to the FR instance for all TDM Atomic Segment types.
tdmRcrdBufferMaxStorageAllocParamOid	 OBJECT IDENTIFIER ::= { 1 3 112 4 4 2 1 70200 1 2 1 1 }

TdmRcrdBufferMaxStorageAlloc	 ::= LongIntUnsigned


-- This parameter configures and reports the retention policy by which TDM Atomic Segments
--  are discarded when the allocated maximum storage is reached. The valid values are:
-- -	‘fifo’
--  - The oldest TDM Segments are discarded first, regardless of the tracking data paths
--  associated with the Segments; 
-- -	‘balanced fifo: The TDM Segments are discarded
--  equally across all tracking data paths for which the recording buffer is holding
--  Segments. The discarding continues until the remaining Segments fit within the allocated
--  storage space.
-- 
tdmRcrdBufferRetentionPolicyParamOid	 OBJECT IDENTIFIER ::= { 1 3 112 4 4 2 1 70200 1 3 1 1 }

TdmRcrdBufferRetentionPolicy	 ::= ENUMERATED
{
	 fifo                	 	 (0)
,	 balancedFifo        	 	 (1)
}



-- This event notifies any change of the tdmRcrdBufferResourceStat parameter.
tdmRcrdBufferResourceStatChangeEventOid	 OBJECT IDENTIFIER ::= { 1 3 112 4 4 2 1 70200 2 1 1 }




-- The event value reports the tdmRcrdBufferResourceStat value that applies since the
--  notified tdmRcrdBufferResourceStatChange event occurred.
tdmRcrdBufferResourceStatChangeValueValueOid	 OBJECT IDENTIFIER ::= { 1 3 112 4 4 2 1 70200 2 1 1 1 }

TdmRcrdBufferResourceStatChangeValue	 ::= TdmRcrdBufferResourceStat


-- This directive permits setting of the controllable parameters of the TdmRcrdBuffer
--  FR type. 
tdmRcrdBufferSetContrParamsDirectiveOid	 OBJECT IDENTIFIER ::= { 1 3 112 4 4 2 1 70200 3 1 1 }




-- The directive qualifier specifies the FR instance the directive shall act on and
--  contains a set of parameter identifier and parameter value pairs. To be valid, the
--  parameter identifier must reference a controllable parameter of the TdmRcrdBuffer
--  FR and the parameter value must be of the same type as the parameter value that
--  shall be set. 
tdmRcrdBufferContrParamIdsAndValuesQualifierOid	 OBJECT IDENTIFIER ::= { 1 3 112 4 4 2 1 70200 3 1 1 1 }

TdmRcrdBufferContrParamIdsAndValues	 ::= DirectiveQualifier


-- none
nonValRmDataStoreFrOid	 OBJECT IDENTIFIER ::= { 1 3 112 4 4 2 1 70300 }




-- None
valRmDataStoreFrOid	 OBJECT IDENTIFIER ::= { 1 3 112 4 4 2 1 70400 }




-- none
ddorRawDataStoreFrOid	 OBJECT IDENTIFIER ::= { 1 3 112 4 4 2 1 70500 }




-- none
openLoopDataStoreFrOid	 OBJECT IDENTIFIER ::= { 1 3 112 4 4 2 1 70600 }




-- None
rtnFileDataStoreFrOid	 OBJECT IDENTIFIER ::= { 1 3 112 4 4 2 1 70700 }




-- None
fwdFileDataStoreFrOid	 OBJECT IDENTIFIER ::= { 1 3 112 4 4 2 1 70800 }




-- none
fspTsProviderFrOid	 OBJECT IDENTIFIER ::= { 1 3 112 4 4 2 1 80100 }




-- This enumerated parameter reports on the status of the service production process
--  used by the given instance of the FSP service. It can take on the following values:
-- -
--  'configured': equipment has been assigned to support the service instance, but the
--  production process is not yet capable of processing Space Packets;
-- - 'operationalBd':
--  the production process has been configured for support, has completed the acquisition
--  sequence, and is capable of processing Space Packets and radiating them in BD transmission
--  mode; the AD transmission mode is currently not supported;
-- - 'operationalAdBd':
--  the production process has been configured for support, has completed the acquisition
--  sequence, and is capable of processing Space Packets and radiating them in any transmission
--  mode;
-- - 'operationalAdSuspended': a TC frame has been transmitted the transmission-limit
--  number of times but no acknowledgement by CLCW has been received; the AD mode has
--  therefore been suspended;
-- - 'interrupted': the production process is stopped due
--  to a fault;
-- - 'halted': the production process is stopped and production equipment
--  is out of service due to management action.
fspProdStatParamOid	 OBJECT IDENTIFIER ::= { 1 3 112 4 4 2 1 80100 1 1 1 1 }

FspProdStat         	 ::= ENUMERATED
{
	 configured          	 	 (0)
,	 operationalBd       	 	 (1)
,	 operationalAdBd     	 	 (2)
,	 operationalAdSuspended	 	 (3)
,	 interrupted         	 	 (4)
,	 halted              	 	 (5)
}



-- This parameter reports the identifier of the given service instance. 
fspSvcInstanceIdParamOid	 OBJECT IDENTIFIER ::= { 1 3 112 4 4 2 1 80100 1 2 1 1 }

FspSvcInstanceId    	 ::= SleSvcInstanceId


-- This enumerated parameter reports the status of the given instance of the FSP service.
--  It can take on the following values:
-- - 'unbound': all resources required to enable
--  the provision of the FSP service have been allocated, and all objects required to
--  provide the service have been instantiated; However, no association yet exists between
--  the user and the provider, i.e., the FSP transfer service provider port is not bound;
-- -
--  'ready': an association has been established between the user and the provider,
--  and they may interact by means of the service operations. However, sending of space
--  packets from the user to the provider (by means of the FSP-TRANSFER-DATA operation)
--  is not permitted; the user may enable the delivery of space packets by means of
--  the appropriate service operation (FSP-START), which, in turn, will cause the provider
--  to transition to the state 'active';
-- - 'active':  this state resembles state ‘ready’,
--  except that now the user can send space packets and the provider is enabled to radiate
--  CLTUs to the spacecraft; the service continues in this state until the user invokes
--  the FSP-STOP operation to cause the provider to suspend transmission of CLTUs and
--  transition back to state 'ready' or the PEER-ABORT invocation to cause the service
--  to transition back to the 'unbound' state.
fspSvcInstanceStateParamOid	 OBJECT IDENTIFIER ::= { 1 3 112 4 4 2 1 80100 1 3 1 1 }

FspSvcInstanceState 	 ::= SleSvcInstanceState


-- This parameter reports the identifier of the peer application, i.e., the authority
--  on whose behalf the SLE application entity is initiating an association with the
--  FSP service provider. The provider performs access control based on this parameter.
--  It may also serve as key to further security relevant information such as the authentication
--  level and method and the related password.
-- 
-- Given the security relevance of this
--  parameter, specific mechanisms for setting this parameter when the FR instance is
--  created and for the transfer of associated security relevant data might be specified
--  in a bilateral agreement between service user and service provider. Also the accessibility
--  by an MD-CSTS instance may be restricted.
fspInitiatorIdParamOid	 OBJECT IDENTIFIER ::= { 1 3 112 4 4 2 1 80100 1 4 1 1 }

FspInitiatorId      	 ::= AuthorityIdentifier


-- This parameter reports the identifier of the FSP application. The user performs access
--  conrol based on this parameter. It may also serve as key to further security relevant
--  information such as the authentication level and method and the related password.
-- 
-- Given
--  the security relevance of this parameter, specific mechanisms for setting this parameter
--  when the FR instance is created and for the transfer of associated security relevant
--  data might be specified in a bilateral agreement between service user and service
--  provider. Also the accessibility by an MD-CSTS instance may be restricted.
fspResponderIdParamOid	 OBJECT IDENTIFIER ::= { 1 3 112 4 4 2 1 80100 1 5 1 1 }

FspResponderId      	 ::= AuthorityIdentifier


-- This parameter reports the port identifier to be used by the user to connect to the
--  service provider. However, the parameter value is only a logical name that needs
--  to be translated into the technology-specific addressing information required to
-- establish
--  a connection with the specific port of the
-- responding SLE application entity. As
--  such this parameter is irrelevant for the service provider, but it may be needed
--  for certain kind of gateways between service user and service provider application.
fspResponderPortIdParamOid	 OBJECT IDENTIFIER ::= { 1 3 112 4 4 2 1 80100 1 6 1 1 }

FspResponderPortId  	 ::= ResponderPortId


-- This parameter reports the setting of the maximum time period in seconds permitted
--  from when a confirmed FSP operation is invoked until the return is received by the
--  invoker.
-- 
-- If a response is not received within that time period, the invoker may
--  invoke the PEER-ABORT operation.
fspRtnTimeoutPeriodParamOid	 OBJECT IDENTIFIER ::= { 1 3 112 4 4 2 1 80100 1 7 1 1 }

FspRtnTimeoutPeriod 	 ::= SleRtnTimeout


-- This enumerated parameter reports the delivery mode of the given instance of the
--  FSP service. For the present version of this service only the ‘forward online’ delivery
--  mode is defined.
fspDeliveryModeParamOid	 OBJECT IDENTIFIER ::= { 1 3 112 4 4 2 1 80100 1 8 1 1 }

FspDeliveryMode     	 ::= ENUMERATED
{
	 fwdOnline           	 	 (0)
}



-- This enumerated parameter reports if the RF lock flag in the CLCW shall be reflected
--  in the service provider’s prodStat parameter. It can take on the following values:
-- -
--  'yes': the ‘No RF available’ flag in the CLCW must be false in order for the provider
--  to set production-status to ‘operational’;
-- - 'no': the CLCW ‘No RF available’ flag
--  shall be ignored.
fspRfAvailableRequiredParamOid	 OBJECT IDENTIFIER ::= { 1 3 112 4 4 2 1 80100 1 9 1 1 }

FspRfAvailableRequired	 ::= ENUMERATED
{
	 yes                 	 	 (0)
,	 no                  	 	 (1)
}



-- This enumerated parameter reports if the bit lock flag in the CLCW shall be reflected
--  in the service provider’s prodStat parameter. It can take on the following values:
-- -
--  'yes': the ‘No bit lock’ flag in the CLCW must be false in order for the provider
--  to set production-status to ‘operational’;
-- - 'no': the CLCW ‘No bit lock’ flag
--  shall be ignored.
fspBitLockRequiredParamOid	 OBJECT IDENTIFIER ::= { 1 3 112 4 4 2 1 80100 1 10 1 1 }

FspBitLockRequired  	 ::= ENUMERATED
{
	 yes                 	 	 (0)
,	 no                  	 	 (1)
}



-- This enumerated parameter reports if the given service instance is permitted to invoke
--  directives. This parameter can take on two values:
-- - 'enabled': this service instance
--  is permitted to invoke directives for the given Virtual Channel;
-- - 'disabled':
--  directives cannot be invoked using this service instance.
fspDirectiveInvocationParamOid	 OBJECT IDENTIFIER ::= { 1 3 112 4 4 2 1 80100 1 11 1 1 }

FspDirectiveInvocation	 ::= ENUMERATED
{
	 enabled             	 	 (0)
,	 disabled            	 	 (1)
}



-- This enumerated parameter reports if the service instance that is permitted to invoke
--  directives for the given VC, if any, is in the state 'active' (cf. fspSiState).
--  At most one service instance for a given VC will be configured to have the capability
--  to invoke directives. This parameter can take on two values:
-- - 'yes': the service
--  instance permitted to invoke directives for the given Virtual Channel is 'active';
-- -
--  'no': it is presently not possible to invoke directives for the given VC, i.e.,
--  the service instance permitted to invoke directives for the given Virtual Channel
--  is in the state 'unbound' or 'ready'.
fspDirectiveInvocationOnlineParamOid	 OBJECT IDENTIFIER ::= { 1 3 112 4 4 2 1 80100 1 12 1 1 }

FspDirectiveInvocationOnline	 ::= ENUMERATED
{
	 yes                 	 	 (0)
,	 no                  	 	 (1)
}



-- This enumerated parameter reports the transmission mode that the given service instance
--  may use for the Space Packets that it processes. This parameter can take on three
--  values: 
-- - 'expedited': the Space Packets will be embedded in TC frames that will
--  be radiated in BD mode;
-- - 'sequenceControlled': the Space Packets will be embedded
--  in TC frames that will be radiated in AD mode; 
-- - 'any': the service supports either
--  transmission mode and will therefore transmit a Space Packet in the mode requested
--  in the FSP-DATA-TRANSFER invocation.
fsp-PermittedTransmissionModeParamOid	 OBJECT IDENTIFIER ::= { 1 3 112 4 4 2 1 80100 1 13 1 1 }

Fsp-PermittedTransmissionMode	 ::= ENUMERATED
{
	 expedited           	 	 (0)
,	 sequenceControlled  	 	 (1)
,	 any                 	 	 (2)
}



-- This parameter reports all APIDs that the Space Packets processed by the given service
--  instance may contain. 
fspApidListParamOid	 OBJECT IDENTIFIER ::= { 1 3 112 4 4 2 1 80100 1 14 1 1 }

FspApidList         	 ::= CHOICE
{

	 -- The FSP SI may process Space Packets with any APID.
	 allApids            	 [0]	 	 NULL
,
	 -- The FSP SI may process only Space Packets with an APID listed here.
	 selectedApids       	 [1]	 	 SEQUENCE  (SIZE( 1 .. 2048))  OF	 INTEGER  (0 .. 2047)
}



-- This parameter reports if cyclic reporting is active and if so it reports  the current
--  setting of the time in seconds between successive FSP-STATUS-REPORT invocations
--  sent by the FSP service provider. 
fspReportingCycleParamOid	 OBJECT IDENTIFIER ::= { 1 3 112 4 4 2 1 80100 1 15 1 1 }

FspReportingCycle   	 ::= SleReportingCycle


-- This parameter reports the value of the packet-identification the FSP service provider
--  expects to receive in the next FSP-TRANSFER-DATA invocation for this invocation
--  to be valid. As long as fspSiState ≠ 'active', the value reported will be zero.
fspExpectedPktIdParamOid	 OBJECT IDENTIFIER ::= { 1 3 112 4 4 2 1 80100 1 16 1 1 }

FspExpectedPktId    	 ::= INTEGER  (0 .. 4294967295)


-- This parameter reports the value of the directive-invocation-identification the FSP
--  service provider expects to receive in the next FSP-INVOKE-DIRECTIVE invocation
--  for this invocation to be valid. The initial value of this parameter is zero.
fspExpectedDirectiveIdParamOid	 OBJECT IDENTIFIER ::= { 1 3 112 4 4 2 1 80100 1 17 1 1 }

FspExpectedDirectiveId	 ::= INTEGER  (0 .. 4294967295)


-- This parameter reports the value of the event-invocation-identification the FSP service
--  provider expects to receive in the next FSP-THROW-EVENT invocation for this invocation
--  to be valid. The initial value of this parameter is zero.
fspExpectedEventInvocIdParamOid	 OBJECT IDENTIFIER ::= { 1 3 112 4 4 2 1 80100 1 18 1 1 }

FspExpectedEventInvocId	 ::= INTEGER  (0 .. 4294967295)


-- This parameter configures and reports the Spacecraft IDs and consequently the Master
--  Channels that are permitted on the given forward link.  
fspTcMcMuxValidScidsParamOid	 OBJECT IDENTIFIER ::= { 1 3 112 4 4 2 1 80100 1 19 1 1 }

FspTcMcMuxValidScids	 ::= SEQUENCE  (SIZE( 1 .. 1024))  OF	 INTEGER  (0 .. 1023)


-- This parameter configures and reports the VC-IDs of the TC VC frames the FR instance
--  accepts as input.
fspTcVcMuxValidTcVcIdsParamOid	 OBJECT IDENTIFIER ::= { 1 3 112 4 4 2 1 80100 1 20 1 1 }

FspTcVcMuxValidTcVcIds	 ::= SEQUENCE  (SIZE( 1 .. 64))  OF	 INTEGER  (0 .. 63)


-- This event notifies any change of the fspProductionStat parameter. 
fspProdStatChangeEventOid	 OBJECT IDENTIFIER ::= { 1 3 112 4 4 2 1 80100 2 1 1 }




-- The event value reports the fspProductionStat value that applies since the notified
--  rafProductionStatChange event occurred.
fspProdStatChangeEventValueValueOid	 OBJECT IDENTIFIER ::= { 1 3 112 4 4 2 1 80100 2 1 1 1 }

FspProdStatChangeEventValue	 ::= FspProdStat


-- This event triggers when a one or more parameters controlling the configuration of
--  service production of the service instance identified by the fspSvcInstanceId parameter
--  have been changed.
-- 
-- This event carries no additional information.
-- 
fspProdConfigurationChangeEventOid	 OBJECT IDENTIFIER ::= { 1 3 112 4 4 2 1 80100 2 2 1 }




-- The event-value of this event is 'empty'.
fspProdConfigurationChangeEventValueValueOid	 OBJECT IDENTIFIER ::= { 1 3 112 4 4 2 1 80100 2 2 1 1 }

FspProdConfigurationChangeEventValue	 ::= ProdConfigurationChangeEventValue


-- The FCltuTsProvider FR provides the to be radiated CLTUs to the tcPlopSyncAndChnlEncode
--  FR.
fCltuTsProviderFrOid	 OBJECT IDENTIFIER ::= { 1 3 112 4 4 2 1 80200 }




-- This enumerated parameter reports the status of the service production process used
--  by the given instance of a F-CLTU service. It can take on the following values:
-- -
--  'configured': equipment has been assigned to support the service instance, but the
--  production process is not yet capable of radiating CLTUs;
-- - 'operational': the
--  production process has been configured for support, has completed the acquisition
--  sequence, and is capable of radiating CLTUs;
-- - 'interrupted': the production process
--  is stopped due to a fault;
-- - 'halted': the production process is stopped and production
--  equipment is out of service due to management action.
fCltuProdStatParamOid	 OBJECT IDENTIFIER ::= { 1 3 112 4 4 2 1 80200 1 1 1 1 }

FCltuProdStat       	 ::= ProdStat


-- This parameter configures and reports the identifier of the given service instance.
--  
fCltuSvcInstanceIdParamOid	 OBJECT IDENTIFIER ::= { 1 3 112 4 4 2 1 80200 1 2 1 1 }

FCltuSvcInstanceId  	 ::= SleSvcInstanceId


-- This enumerated parameter reports the status of the given instance of the F-CLTU
--  service. It can take on the following values:
-- - 'unbound': all resources required
--  to enable the provision of the Forward CLTU service have been allocated, and all
--  objects required to provide the service have been instantiated; however, no association
--  yet exists between the user and the provider, i.e., the F-CLTU transfer service
--  provider port is not bound;
-- - 'ready': an association has been established between
--  the user and the provider, and they may interact by means of the service operations.
--  However, sending of CLTUs from the user to the provider (by means of the CLTU-TRANSFER-DATA
--  operation) is not permitted; the user may enable the delivery of CLTUs by means
--  of the appropriate service operation (CLTU-START), which, in turn, will cause the
--  provider to transition to the state 'active';
-- - 'active':  this state resembles
--  state ‘ready’, except that now the user can send CLTUs and the provider is enabled
--  to radiate CLTUs to the spacecraft; the service continues in this state until the
--  user invokes either the CLTU-STOP operation to cause the provider to suspend transmission
--  of CLTUs and transition back to state 'ready' or the user invokes the PEER-ABORT
--  operation to cause the service to transition back to the 'unbound' state.
fCltuSvcInstanceStateParamOid	 OBJECT IDENTIFIER ::= { 1 3 112 4 4 2 1 80200 1 3 1 1 }

FCltuSvcInstanceState	 ::= SleSvcInstanceState


-- This parameter reports the identifier of the peer application, i.e., the authority
--  on whose behalf the SLE application entity is initiating an association with the
--  FCLTU service provider. The provider performs access control based on this parameter.
--  It may also serve as key to further security relevant information such as the authentication
--  level and method and the related password.
-- 
-- Given the security relevance of this
--  parameter, specific mechanisms for setting this parameter when the FR instance is
--  created and for the transfer of associated security relevant data might be specified
--  in a bilateral agreement between service user and service provider. Also the accessibility
--  by an MD-CSTS instance may be restricted.
fCltuInitiatorIdParamOid	 OBJECT IDENTIFIER ::= { 1 3 112 4 4 2 1 80200 1 4 1 1 }

FCltuInitiatorId    	 ::= AuthorityIdentifier


-- This parameter reports the identifier of the FCLTU application. The user performs
--  access conrol based on this parameter. It may also serve as key to further security
--  relevant information such as the authentication level and method and the related
--  password.
-- 
-- Given the security relevance of this parameter, specific mechanisms
--  for setting this parameter when the FR instance is created and for the transfer
--  of associated security relevant data might be specified in a bilateral agreement
--  between service user and service provider. Also the accessibility by an MD-CSTS
--  instance may be restricted.
fCltuResponderIdParamOid	 OBJECT IDENTIFIER ::= { 1 3 112 4 4 2 1 80200 1 5 1 1 }

FCltuResponderId    	 ::= AuthorityIdentifier


-- This parameter reports the port identifier to be used by the user to connect to the
--  service provider. However, the parameter value is only a logical name that needs
--  to be translated into the technology-specific addressing information required to
--  establish a connection with the specific port of the
-- responding SLE application
--  entity. As such this parameter is irrelevant for the service provider, but it may
--  be needed for certain kind of gateways between service user and service provider
--  application.
fCltuResponderPortIdParamOid	 OBJECT IDENTIFIER ::= { 1 3 112 4 4 2 1 80200 1 6 1 1 }

FCltuResponderPortId	 ::= ResponderPortId


-- This parameter configures and reports the setting of the maximum time period in seconds
--  permitted from when a confirmed F-CLTU operation is invoked until the return has
--  to be received by the invoker.
-- 
-- If a response is not received within that time
--  period, the invoker may invoke the PEER-ABORT operation.
fCltuRtnTimeoutPeriodParamOid	 OBJECT IDENTIFIER ::= { 1 3 112 4 4 2 1 80200 1 7 1 1 }

-- The engineering unit of this parameter is second.
FCltuRtnTimeoutPeriod	 ::= SleRtnTimeout


-- This enumerated parameter reports the delivery mode of the given instance of the
--  F-CLTU service. For the present version of this service only the ‘fwdOnline’ delivery
--  mode is defined.
fCltuDeliveryModeParamOid	 OBJECT IDENTIFIER ::= { 1 3 112 4 4 2 1 80200 1 8 1 1 }

FCltuDeliveryMode   	 ::= ENUMERATED
{
	 fwdOnline           	 	 (0)
}



-- This enumerated parameter configures and reports how the F-CLTU provider notifies
--  certain changes of fCltuProductionStat to the service user. It can take on two values:
-- -
--  'immediate': the user is notified of a fCltuProductionStat change to 'interrupted'
--  as soon as this transition is detected;
-- - 'deferred': the user is notified about
--  the fCltuProductionStat change only if and when the radiation of a CLTU is affected.
fCltuNotificationModeParamOid	 OBJECT IDENTIFIER ::= { 1 3 112 4 4 2 1 80200 1 9 1 1 }

FCltuNotificationMode	 ::= ENUMERATED
{
	 immediate           	 	 (0)
,	 deferred            	 	 (1)
}



-- This enumerated parameter configures and reports the way the F-CLTU service provider
--  will act in the event of a protocol abort. This parameter can take on two values:
-- -
--  'abort': service production will cease in the event of a protocol abort;
-- - 'continue':
--  service production will disregard the protocol abort event and continue radiating
--  the CLTUs already buffered at the time of the event.
fCltuProtocolAbortModeParamOid	 OBJECT IDENTIFIER ::= { 1 3 112 4 4 2 1 80200 1 10 1 1 }

FCltuProtocolAbortMode	 ::= ENUMERATED
{
	 abort               	 	 (0)
,	 continue            	 	 (1)
}



-- This parameter reports the current setting of the time in seconds between successive
--  CLTU-STATUS-REPORT invocations sent by the F-CLTU service provider provided fCltuReportingCycle
--  is 'on'. When fCltuReportingCycle is 'off', no cycle time is reported. 
fCltuReportingCycleParamOid	 OBJECT IDENTIFIER ::= { 1 3 112 4 4 2 1 80200 1 11 1 1 }

-- If applicable, the engineering unit of this parameter is second.
FCltuReportingCycle 	 ::= SleReportingCycle


-- This parameter reports the value of the cltu-identification the F-CLTU service provider
--  expects to receive in the next CLTU-TRANSFER-DATA invocation for this invocation
--  to be valid. As long as fCltuSiState ≠ 'active', the value reported will be zero.
fCltuExpectedCltuIdParamOid	 OBJECT IDENTIFIER ::= { 1 3 112 4 4 2 1 80200 1 12 1 1 }

FCltuExpectedCltuId 	 ::= INTEGER  (0 .. 4294967295)


-- This parameter reports the value of the event-invocation-identification the F-CLTU
--  service provider expects to receive in the next CLTU-THROW-EVENT invocation for
--  this invocation to be valid. The initial value of this parameter is zero.
fCltuExpectedEventInvocIdParamOid	 OBJECT IDENTIFIER ::= { 1 3 112 4 4 2 1 80200 1 13 1 1 }

FCltuExpectedEventInvocId	 ::= INTEGER  (0 .. 4294967295)


-- This parameter reports the total number of CLTUs received while the given service
--  instance has been accessible to the user. Only CLTUs that the service provider accepted
--  and consequently buffered are counted in the total.
fCltuNumberOfCltusReceivedParamOid	 OBJECT IDENTIFIER ::= { 1 3 112 4 4 2 1 80200 1 14 1 1 }

FCltuNumberOfCltusReceived	 ::= INTEGER  (0 .. 4294967295)


-- This parameter reports the number of CLTUs that the provider attempted to radiate
--  while the given service instance has been active including
-- - CLTUs that radiated
--  successfully;
-- - CLTUs that expired;
-- - CLTUs that aborted;
-- - a CLTU in the process
--  of being radiated.
fCltuNumberOfCltusProcessedParamOid	 OBJECT IDENTIFIER ::= { 1 3 112 4 4 2 1 80200 1 15 1 1 }

FCltuNumberOfCltusProcessed	 ::= INTEGER  (0 .. 4294967295)


-- This parameter reports the number of CLTUs that the provider successfully radiated
--  completely during the service provision period. A CLTU in the process of being radiated
--  is not included in this count.
fCltuNumberOfCltusRadiatedParamOid	 OBJECT IDENTIFIER ::= { 1 3 112 4 4 2 1 80200 1 16 1 1 }

FCltuNumberOfCltusRadiated	 ::= INTEGER  (0 .. 4294967295)


-- This event notifies any change of the fCltuProdStat parameter and the prodStat value
--  applicable since the event occurred.
fCltuProdStatChangeEventOid	 OBJECT IDENTIFIER ::= { 1 3 112 4 4 2 1 80200 2 1 1 }




-- The event value reports the fCltuProductionStat value that applies since the notified
--  fCltuProductionStatChange event has occurred.
fCltuProdStatChangeEventValueValueOid	 OBJECT IDENTIFIER ::= { 1 3 112 4 4 2 1 80200 2 1 1 1 }

FCltuProdStatChangeEventValue	 ::= FCltuProdStat


-- This event triggers when a one or more parameters controlling the configuration of
--  service production of the service instance identified by the fCltuSvcInstanceId
--  parameter have been changed.
-- 
-- This event carries no additional information.
-- 
fCltuProdConfigurationChangeEventOid	 OBJECT IDENTIFIER ::= { 1 3 112 4 4 2 1 80200 2 2 1 }




-- The event-value of this event is 'empty'.
fCltuProdConfigurationChangeEventValueValueOid	 OBJECT IDENTIFIER ::= { 1 3 112 4 4 2 1 80200 2 2 1 1 }

FCltuProdConfigurationChangeEventValue	 ::= ProdConfigurationChangeEventValue


-- This directive permits setting of the controllable parameters of the FCltuTsProvider
--  FR type. 
fCltuSetContrParamsDirectiveOid	 OBJECT IDENTIFIER ::= { 1 3 112 4 4 2 1 80200 3 1 1 }




-- The directive qualifier specifies the FR instance the directive shall act on and
--  contains a set of parameter identifier and parameter value pairs. To be valid, the
--  parameter identifier must reference a controllable parameter of the FCltuTsProvider
--  FR and the parameter value must be of the same type as the parameter value that
--  shall be set.
fCltuContrParamIdsAndValuesQualifierOid	 OBJECT IDENTIFIER ::= { 1 3 112 4 4 2 1 80200 3 1 1 1 }

FCltuContrParamIdsAndValues	 ::= DirectiveQualifier


-- The Forward Frame CSTS Provider functional resource provides service-user-generated
--  Space Link Protocol Data Units (SL-PDUs: transfer frames or Channel Access Data
--  Units) to a functional resource in the Synchronization and Channel Coding FR Stratum.
--  Each instance of the Forward Frame CSTS Provider FR type must be configured to transfer
--  SL-PDUs that conform to the specific Synchronization and Channel Coding FR Set that
--  it accesses. The functions of the Forward Frame CSTS Provider are specified in CCSDS
--  922.3.
fwdFrameCstsProviderFrOid	 OBJECT IDENTIFIER ::= { 1 3 112 4 4 2 1 80300 }




-- This parameter reports the production status of the Forward Frame service instance.
--  This parameter can take on one of four values:
--  - 'configured': all production
--  functions needed to support this service instance have been configured ;
--  - ‘operational’:
--  all production functions have been enabled to process data for this service instance;
-- 
--  - ‘interrupted’: one or more production functions have been stopped because of an
--  error condition that may be temporary;
--  - ‘halted’: one or more production functions
--  have been stopped by management action.
-- 
ffSvcProdStatParamOid	 OBJECT IDENTIFIER ::= { 1 3 112 4 4 2 1 80300 1 1 1 1 }

FfSvcProdStat       	 ::= ProdStat


-- This parameter configures and reports the service instance identifier used in the
--  PDUs exchanged between the user and provider of the Forward Frame service instance.
--  
ffSvcInstanceIdParamOid	 OBJECT IDENTIFIER ::= { 1 3 112 4 4 2 1 80300 1 2 1 1 }

FfSvcInstanceId     	 ::= CstsSvcInstanceId


-- This enumerated parameter reports the status of the given instance of the Forward
--  Frame service. It can take on the following values:
--  - 'unbound': all resources
--  required to enable the provision of the service have been allocated, and all objects
--  required to provide the service have been instantiated; However, no association
--  yet exists between the user and the provider, i.e., the transfer service provider
--  port is not bound;
--  - 'boundReady': an association has been established between
--  the user and the provider, and they may interact by means of the service operations.
--  However, sending of SLPDUs from the user to the provider (by means of the PROCESS-DATA
--  operation) is not permitted; the user may enable the transfer of SLPDUs by means
--  of the appropriate service operation (START), which, in turn, will cause the provider
--  to transition to the state 'boundActive';
--  - 'boundActive': this state resembles
--  state ‘boundReady’, except that now the user can send SLPDUs and the provider is
--  enabled  to radiate them to the target Space User Node; the service continues in
--  this state until the user invokes (a) the STOP operation to cause the provider to
--  suspend transmission of SLPDUs and transition back to state 'boundReady' or (b)
--  the PEER-ABORT invocation to cause the service to transition back to the 'unbound'
--  state.
-- 
ffSvcInstanceStateParamOid	 OBJECT IDENTIFIER ::= { 1 3 112 4 4 2 1 80300 1 3 1 1 }

FfSvcInstanceState  	 ::= StatefulCstsInstanceState


-- This parameter reports the identifier of the peer application, i.e., the authority
--  on whose behalf the CSTS application entity is initiating an association with the
--  Forward Frame service provider. The provider performs access control based on this
--  parameter. It may also serve as key to further security relevant information such
--  as the authentication level and method and the related password.
-- 
-- Given the security
--  relevance of this parameter, specific mechanisms for setting this parameter when
--  the FR instance is created and for the transfer of associated security relevant
--  data might be specified in a bilateral agreement between service user and service
--  provider. Also the accessibility by an MD-CSTS instance may be restricted.
ffInitiatorIdParamOid	 OBJECT IDENTIFIER ::= { 1 3 112 4 4 2 1 80300 1 4 1 1 }

FfInitiatorId       	 ::= AuthorityIdentifier


-- This parameter reports the identifier of the Forward Frame service application. The
--  user performs access conrol based on this parameter. It may also serve as key to
--  further security relevant information such as the authentication level and method
--  and the related password.
-- 
-- Given the security relevance of this parameter, specific
--  mechanisms for setting this parameter when the FR instance is created and for the
--  transfer of associated security relevant data might be specified in a bilateral
--  agreement between service user and service provider. Also the accessibility by an
--  MD-CSTS instance may be restricted.
ffResponderIdParamOid	 OBJECT IDENTIFIER ::= { 1 3 112 4 4 2 1 80300 1 5 1 1 }

FfResponderId       	 ::= AuthorityIdentifier


-- This parameter configures and reports the logical name of the port used by the underlying
--  communication service to respond to invocation on this service instance. The logical
--  name is translated internally by the service provider to a port identifier that
--  is appropriate to the underlying communication service.
-- 
-- This parameter configures
--  and reports the port identifier to be used by the user to connect to the service
--  provider. However, the parameter value is only a logical name that needs to be translated
--  into the technology-specific addressing information required to establish a connection
--  with the specific port of the responding CSTS application entity. As such this parameter
--  is irrelevant for the service provider, but it may be needed for certain kind of
--  gateways between service user and service provider application.
-- 
-- 
ffResponderPortIdParamOid	 OBJECT IDENTIFIER ::= { 1 3 112 4 4 2 1 80300 1 6 1 1 }

FfResponderPortId   	 ::= ResponderPortId


-- This parameter configures and reports the time (in seconds) that the service user
--  should wait before invoking a PEER-ABORT when a return has not been received in
--  response to a BIND or UNBIND invocation.
ffSvcUserRespondingTimerParamOid	 OBJECT IDENTIFIER ::= { 1 3 112 4 4 2 1 80300 1 7 1 1 }

FfSvcUserRespondingTimer	 ::= SvcUserRespTimer


-- This parameter configures and reports if the data processing mode of the service
--  instance. This complex parameter can have one of two values:
--  - 'sequenceControlled':
--  the Sequence-Controlled Frame Data Processing procedure is the prime procedure type;
-- 
--  - 'bufferedData’: the Buffered Frame Data Processing procedure is the prime procedure
--  type.
-- 
-- The ‘bufferedData’ value is further qualified to (a) specify  the transfer
--  mode as either:
-- - 'complete'; or
--  - timely‘
-- and (b) to specify the Maximum Forward
--  Buffer Size and Processing Latency Limit
ffDataProcessingModeParamOid	 OBJECT IDENTIFIER ::= { 1 3 112 4 4 2 1 80300 1 8 1 1 }

FfDataProcessingMode	 ::= CHOICE
{
	 sequenceControlled  	 [0]	 	 NULL
,	 bufferedData        	 [1]	 	 SEQUENCE
	 {

	 	 -- This parameter configures and reports the buffered-data transfer mode of the service
	 	 --  instance. 
	 	 dataTransferMode    	 ENUMERATED
	 	 {
	 	 	 complete            	 	 (0)
	 	 ,	 timely              	 	 (1)
	 	 }

,
	 	 -- This parameter configures and reports the initial value of the maximum size allowed
	 	 --  in for incoming Forward Buffers, in number of PROCESS-DATA invocations
	 	 maxFwdBufferSize    	 LongIntPos
,
	 	 -- The initial value of the processing latency limit in milliseconds, for the data processing
	 	 --  procedure of the service instance
	 	 processingLatencyLimit	 LongIntPos
	 }

}



-- bit mask values are This parameter configures and reports (a) the bit pattern that
--  specifies the Global VCID that authorized to use the Forward Frame service instance,
--  and (b) the bit mask to applied to the first four octets of each incoming transfer
--  frame) to mask out any bits that are not used to ascertain whether the Global VCID
--  of that transfer frame is authorized to use the Forward Frame service instance.
-- 
-- For
--  TC and AOS frames, only the bits corresponding to the TFVN, SCID, and VCID are set
--  to their correct values, and all other bits in the 4-octet field are set to 0. 
-- 
-- For
--  USLP frames, only the bits corresponding to the TFVN, SCID, Source or Destination
--  ID,and VCID are set to their correct values, and all other bits in the 4-octet field
--  are set to 0.
-- 
-- For TC, AOS, or USLP frames, the bit mask values are predefined
--  and do not need to be specified in the configuration paramters.
-- 
-- For CADUs, the
--  headers are not checked, regardless of the enclosed frame types, and the bit mask
--  is predefined to allow any values in the forst 4 octets of the CADU.
-- 
-- For frames
--  that do not conform to TC, AOS, or USLP frame formats but still need to have the
--  first 4 octets validated, the 'other' value allows the user to specify the allowed
--  bit pattern and the bit mask that validates that bit pattern.
-- 
-- 
-- 
ffAuthorizedGvcidAndBitMaskParamOid	 OBJECT IDENTIFIER ::= { 1 3 112 4 4 2 1 80300 1 9 1 1 }

FfAuthorizedGvcidAndBitMask	 ::= CHOICE
{

	 -- When TC frames are used, the bits corresponding to the TFVN (bits 0-1 = '00' binary)
	 --  , SCID (bits 6-15), and VCID (bits 16-21) are set to their correct values, and all
	 --  other bits in the 4-octet field are set to 0. The value of the gvcid-bit-mask configuration
	 --  parameter shall be C3 FF FC 00  Hex.
	 tcGvcid             	 [0]	 	 SEQUENCE
	 {
	 	 tcScid              	 INTEGER  (0 .. 1023)
,	 	 tcVcid              	 INTEGER  (0 .. 63)
	 }

,
	 -- When AOS frames are used, the bits corresponding to the TFVN (bits 0-1 = '01' binary),
	 --  SCID (bits 2-9), and VCID (bits 10-15) are set to their correct values, and all
	 --  other bits in the 4-octet field are set to 0. The value of the gvcid-bit-mask configuration
	 --  parameter shall be FF FF 00 00 Hex
	 aosGvcid            	 [1]	 	 SEQUENCE
	 {
	 	 aosScid             	 INTEGER  (0 .. 255)
,	 	 aosVcid             	 INTEGER  (0 .. 63)
	 }

,
	 -- When USLP frames are used,  the bits corresponding to the TFVN (bits 0-3 = '1100'),
	 --  SCID (bits 4-19), Source or Destination ID (bit20),and VCID (bits 21-26) are set
	 --  to their correct values, and all other bits in the 4-octet field are set to 0. The
	 --  value of the gvcid-bit-mask configuration parameter shall be FF FF FF E0 Hex
	 uslpGvcid           	 [2]	 	 SEQUENCE
	 {
	 	 uslpScid            	 INTEGER  (0 .. 65535)
,	 	 uslpVcid            	 INTEGER  (0 .. 63)
	 }

,
	 -- When a CADU is used, no frame header checking is performed, regardeless of the space
	 --  link protocol. The first 4 octets may contain any value, and the value of the gvcid-bit-mask
	 --  configuration parameter shall be 00 00 00 00  Hex.
	 cadu                	 [3]	 	 NULL
,
	 -- For frames that do not conform to the TC, AOS, or USLP formats, the content of the
	 --  Authorized GVCID and the structure of the Bit Mask is defined by the user.
	 other               	 [4]	 	 SEQUENCE
	 {
	 	 otherBitMask        	 OCTET STRING (SIZE( 4)) 
,
	 	 -- For other frame types, the authorized value can be any bit pattern that is appropriate
	 	 --  to the first 4 octets of that frame type.
	 	 otherAuthorizedValue	 OCTET STRING (SIZE( 4)) 
	 }

}



-- This parameter configures and reports the minimum permitted length, in octets, for
--  incoming space link protocol data units (e.g., transfer frames).
ffMinFrameLengthParamOid	 OBJECT IDENTIFIER ::= { 1 3 112 4 4 2 1 80300 1 10 1 1 }

FfMinFrameLength    	 ::= ShortIntPos


-- This parameter configures and reports the maximum permitted length, in octets, for
--  incoming space link protocol data units (e.g., transfer frames). 
-- The maximum permitted
--  length must be equal to or greater than the minimum permitted length (fFrameMinFrameLength).
-- 
ffMaxFrameLengthParamOid	 OBJECT IDENTIFIER ::= { 1 3 112 4 4 2 1 80300 1 11 1 1 }

FfMaxFrameLength    	 ::= ShortIntPos


-- This parameter configures and reports the initial value of the Input Queue size (that
--  is, the size of the queue upon the binding of the service instance), in number of
--  PROCESS-DATA invocations, for the data processing procedure of the service instance.
ffInputQueueSizeParamOid	 OBJECT IDENTIFIER ::= { 1 3 112 4 4 2 1 80300 1 12 1 1 }

FfInputQueueSize    	 ::= LongIntPos


-- This parameter configures and reports the minimum allowed delivery cycle, in milliseconds,
--  to which any instance of the Cyclic Report procedure can be set.
-- 
-- If the Cyclic
--  Report procedure is not present in the implementation of the service, this paramter
--  shall be undefined.
ffMinAllowedDeliveryCycleParamOid	 OBJECT IDENTIFIER ::= { 1 3 112 4 4 2 1 80300 1 13 1 1 }

FfMinAllowedDeliveryCycle	 ::= MinAllowedDeliveryCycle


-- This parameter configures and reports the set of Event Label Lists used by the Notification
--  procedures of the service instance.
-- The Notification procedures is optional for
--  implementations of the Forward Frame service. If the service implementation does
--  not support this procedure, or if it is supported but there are no label lists,
--  this parameter is not set and if queried the parameter qualifier shall be 'undefined'.
ffNamedEventLabelListsParamOid	 OBJECT IDENTIFIER ::= { 1 3 112 4 4 2 1 80300 1 14 1 1 }

-- The values of the paramOrEventId components are constrained to be event identifiers
FfNamedEventLabelLists	 ::= LabelListSetV2


-- This parameter configures and reports whether the service instance is enabled to
--  invoke directives on the production functional resources instances that directly
--  support it. This parameter can take on two values:
--  - 'enabled';
--  - ‘disabled’.
-- If
--  the Master Throw Event procedure is not implemented for the service instance, this
--  parameter is undefined and ignored in the configuration of the functional  resource.
ffMasterThrowEventEnabledParamOid	 OBJECT IDENTIFIER ::= { 1 3 112 4 4 2 1 80300 1 15 1 1 }

FfMasterThrowEventEnabled	 ::= ENUMERATED
{
	 enabled             	 	 (0)
,	 disabled            	 	 (1)
}



-- This parameter configures and reports the set of Parameter Label Lists used by the
--  Cyclic Report and/or Information Query procedures of the service instance.
-- 
-- NOTE
--  - Both the Cyclic Report and Information Query procedures are optional for implementations
--  of the Forward Frame service. If the service implementation supports neither of
--  these procedures, or if either or both are supported but there are no label lists,
--  this parameter is not set and if queried the parameter qualifier shall be 'undefined'.
ffNamedParamLabelListsParamOid	 OBJECT IDENTIFIER ::= { 1 3 112 4 4 2 1 80300 1 16 1 1 }

-- the values of the paramOrEventId components are constrained to be parameter identifiers
FfNamedParamLabelLists	 ::= LabelListSetV2


-- This parameter reports the number of space link protocol data units (e.g., frames),
--  in number of PROCESS-DATA invocations, received by the data processing procedure
--  of the service instance since the beginning of the Service Instance Provision Period.
--  
ffNumberDataUnitsRcvdParamOid	 OBJECT IDENTIFIER ::= { 1 3 112 4 4 2 1 80300 1 17 1 1 }

FfNumberDataUnitsRcvd	 ::= LongIntUnsigned


-- This parameter reports the number of spalce link protocol data units (e.g., frames)
--  , in number of PROCESS-DATA invocations, submitted by the data processing procedure
--  of the service instance to service production processing  since the beginning of
--  the Service Instance Provision Period. 
ffNumberDataUnitsToProcessingParamOid	 OBJECT IDENTIFIER ::= { 1 3 112 4 4 2 1 80300 1 18 1 1 }

FfNumberDataUnitsToProcessing	 ::= LongIntUnsigned


-- This parameter reports the number of space link protocol data units (e.g., frames)
--  in number of PROCESS-DATA invocations, that have been reported by service production
--  to have completed processing – i.e., to have been radiated - since the beginning
--  of the Service Instance Provision Period
ffNumberDataUnitsProcessedParamOid	 OBJECT IDENTIFIER ::= { 1 3 112 4 4 2 1 80300 1 19 1 1 }

FfNumberDataUnitsProcessed	 ::= LongIntUnsigned


-- This event notifies that the value of ffSvcProdStat has changed.
-- 
ffSvcProdStatChangeEventOid	 OBJECT IDENTIFIER ::= { 1 3 112 4 4 2 1 80300 2 1 1 }




-- This event carries the new value of the production status following the change:
-- 
--  - 'configured': all production functions needed to support this service instance
--  are configured ;
--  - ‘operational’: all production functions have been enabled to
--  process data for this service instance;
--  - ‘interrupted’: one or more production
--  functions have been stopped because of an error condition that may be temporary;
-- 
--  - ‘halted’: one or more production functions have been stopped by management action.
ffSvcProdStatChangeValueValueOid	 OBJECT IDENTIFIER ::= { 1 3 112 4 4 2 1 80300 2 1 1 1 }

FfSvcProdStatChangeValue	 ::= FfSvcProdStat


-- This event triggers when a one or more parameters controlling the configuration of
--  service production have been changed.
-- 
-- This event carries no additional information.
ffSvcProdConfgurationChangeEventOid	 OBJECT IDENTIFIER ::= { 1 3 112 4 4 2 1 80300 2 2 1 }




-- The value of this event is 'empty'
ffSvcProdConfgurationChangeValueValueOid	 OBJECT IDENTIFIER ::= { 1 3 112 4 4 2 1 80300 2 2 1 1 }

FfSvcProdConfgurationChangeValue	 ::= ProdConfigurationChangeEventValue


-- The RafTsProvider accepts as input the frame provided by the FlfSyncAndDecode and
--  the OfflineFrameBuffer FRs.
rafTsProviderFrOid	 OBJECT IDENTIFIER ::= { 1 3 112 4 4 2 1 80400 }




-- This enumerated parameter reports the status of the service production process used
--  by the given instance of an RAF service. It can take on the following values:
-- -
--  'running' - the RAF production process is capable of processing a return space link
--  physical channel, if available;
-- - 'interrupted' - the RAF production process is
--  stopped due to a fault;
-- - 'halted' - the RAF production process is stopped and production
--  equipment is out of service due to management action.
rafProdStatParamOid	 OBJECT IDENTIFIER ::= { 1 3 112 4 4 2 1 80400 1 1 1 1 }

RafProdStat         	 ::= SleRtnProdStat


-- This parameter configures and reports the identifier of the given service instance.
--  
rafSvcInstanceIdParamOid	 OBJECT IDENTIFIER ::= { 1 3 112 4 4 2 1 80400 1 2 1 1 }

RafSvcInstanceId    	 ::= SleSvcInstanceId


-- This enumerated parameter reports the status of the given instance of the RAF service.
--  It can take on the following values:
-- - 'unbound' - All resources required to enable
--  the provision of the RAF service have been allocated, and all objects required to
--  provide the service have been instantiated; however, no association yet exists between
--  the user and the provider, i.e., the RAF transfer service provider port is not bound;
-- -
--  'ready'- An association has been established between the user and the provider,
--  and they may interact by means of the service operations. However, sending of telemetry
--  frames from the provider to the user (by means of the RAF-TRANSFER-DATA operation)
--  is not permitted; the user may enable the delivery of telemetry frames by means
--  of the appropriate service operation (RAF-START), which, in turn, will cause the
--  provider to transition to the rafSiState 'active';
-- - 'active' -  This state resembles
--  the rafSiState ‘ready’, except that now the provider will send telemetry frames
--  provided frames of the selected characteristics are made available by the RAF production
--  process; the service continues in this state until the user invokes either the RAF-STOP
--  operation to cause the provider to suspend delivery of telemetry frames and transition
--  back to the rafSiState 'ready' or the PEER-ABORT invocation to cause the service
--  to transition back to the rafSiState 'unbound'.
rafSvcInstanceStateParamOid	 OBJECT IDENTIFIER ::= { 1 3 112 4 4 2 1 80400 1 3 1 1 }

RafSvcInstanceState 	 ::= SleSvcInstanceState


-- This parameter reports the identifier of the peer application, i.e., the authority
--  on whose behalf the SLE application entity is initiating an association with the
--  RAF service provider. The provider performs access control based on this parameter.
--  It may also serve as key to further security relevant information such as the authentication
--  level and method and the related password.
-- 
-- Given the security relevance of this
--  parameter, specific mechanisms for setting this parameter when the FR instance is
--  created and for the transfer of associated security relevant data might be specified
--  in a bilateral agreement between service user and service provider. Also the accessibility
--  by an MD-CSTS instance may be restricted.
rafInitiatorIdParamOid	 OBJECT IDENTIFIER ::= { 1 3 112 4 4 2 1 80400 1 4 1 1 }

RafInitiatorId      	 ::= AuthorityIdentifier


-- This parameter reports the identifier of the RAF application. The user performs access
--  conrol based on this parameter. It may also serve as key to further security relevant
--  information such as the authentication level and method and the related password.
-- 
-- Given
--  the security relevance of this parameter, specific mechanisms for setting this parameter
--  when the FR instance is created and for the transfer of associated security relevant
--  data might be specified in a bilateral agreement between service user and service
--  provider. Also the accessibility by an MD-CSTS instance may be restricted.
rafResponderIdParamOid	 OBJECT IDENTIFIER ::= { 1 3 112 4 4 2 1 80400 1 5 1 1 }

RafResponderId      	 ::= AuthorityIdentifier


-- This parameter reports the port identifier to be used by the user to connect to the
--  service provider. However, the parameter value is only a logical name that needs
--  to be translated into the technology-specific addressing information required to
-- establish
--  a connection with the specific port of the
-- responding SLE application entity. As
--  such this parameter is irrelevant for the service provider, but it may be needed
--  for certain kind of gateways between service user and service provider application.
rafResponderPortIdParamOid	 OBJECT IDENTIFIER ::= { 1 3 112 4 4 2 1 80400 1 6 1 1 }

RafResponderPortId  	 ::= ResponderPortId


-- This parameter reports the setting of the maximum time period in seconds permitted
--  from when a confirmed RAF operation is invoked until the return is received by the
--  invoker.
-- 
-- If a response is not received within that time period, the invoker may
--  invoke the PEER-ABORT operation.
rafRtnTimeoutPeriodParamOid	 OBJECT IDENTIFIER ::= { 1 3 112 4 4 2 1 80400 1 7 1 1 }

-- The engineering unit of this parameter is second.
RafRtnTimeoutPeriod 	 ::= SleRtnTimeout


-- This enumerated parameter configures and reports the delivery mode of the given RAF
--  service instance. It can take on three values:
-- - 'online timely'  - the timely
--  online delivery mode limits the size of the backlog of not yet delivered data that
--  is allowed to accumulate by discarding data that cannot be delivered within a certain
--  time. Furthermore, when data is discarded, it is discarded ‘in chunks’, i.e., as
--  a sufficiently large block of contiguous frames rather than as random frames here
--  and there; in general, this approach maximizes the usefulness of the data that is
--  delivered.
-- - 'online complete' - this delivery mode attempts to deliver all acquired
--  frames having the user selected characteristics, in order, with minimum delay consistent
--  with the available ground communications bandwidth. To that end, the service provider
--  has a buffer sufficiently large to deal with communications service delays, outages,
--  and bandwidth limitations;
-- - 'offline' - in this delivery mode, the provider side
--  buffer enables data to be delivered hours or days after their acquisition. To that
--  end, this buffer is sufficiently large to hold all data that might be accumulated
--  during several space link sessions.
rafDeliveryModeParamOid	 OBJECT IDENTIFIER ::= { 1 3 112 4 4 2 1 80400 1 8 1 1 }

RafDeliveryMode     	 ::= SleRtnDeliveryMode


-- This parameter configures and reports the maximum allowable delivery latency time,
--  in seconds, for the online delivery modes, i.e., the maximum delay from when the
--  frame is acquired by the provider until it is delivered to the user.  If rafDeliveryMode
--  = 'offline', rafLatencyLimit has no effect.
rafLatencyLimitParamOid	 OBJECT IDENTIFIER ::= { 1 3 112 4 4 2 1 80400 1 9 1 1 }

-- The engineering unit of this parameter is second
RafLatencyLimit     	 ::= INTEGER  (1 .. 100)


-- This parameter configures and reports the number of frames the provider shall block
--  in one RAF-PDU before passing it to the underlying communications layer except if
--  expiry of the rafLatencyLimit requires earlier release of the RAF-PDU.
rafTransferBufferSizeParamOid	 OBJECT IDENTIFIER ::= { 1 3 112 4 4 2 1 80400 1 10 1 1 }

RafTransferBufferSize	 ::= INTEGER  (1 .. 1000)


-- This enumerated parameter reports the set of the quality of the frames that the user
--  may select with the given RAF service instance. The permitted frame quality settings
--  must be chosen from the following set of values: 
-- - 'good' - only frames that based
--  on successful RS or LDPC decoding/correcting and/or based on the check of the FECF
--  are assumed to be error free will be delivered to the user;
-- - 'erred' - only frames
--  that based on unsuccessful RS or LDPC decoding/correcting or  based on the failed
--  check of the FECF were found to contain errors will be delivered to the user;
-- -
--  'all'  - all frames regardless if error free or not are delivered to the user; this
--  includes telemetry frames for which due to lack of compatibility with the pertinent
--  CCSDS Recommendations the quality cannot be determined.
rafPermittedFrameQualityParamOid	 OBJECT IDENTIFIER ::= { 1 3 112 4 4 2 1 80400 1 11 1 1 }

RafPermittedFrameQuality	 ::= SET  (SIZE( 1 .. 3))  OF	 ENUMERATED
	 {
	 	 good                	 	 (0)
	 ,	 erred               	 	 (1)
	 ,	 all                 	 	 (2)
	 }



-- This enumerated parameter reports the quality of the frames that shall be delivered
--  by the given RAF service instance. It can take on one of three values:
-- - 'good'
--  - only frames that based on successful RS or LDPC decoding/correcting and/or based
--  on the check of the FECF are assumed to be error free will be delivered to the user;
-- -
--  'erred' - only frames that based on unsuccessful RS or LDPC decoding/correcting
--  and/or based on the failed check of the FECF were found to contain errors will be
--  delivered to the user;
-- - 'all'  - all frames regardless if error free or not are
--  delivered to the user; this includes telemetry frames for which due to lack of compatibility
--  with the pertinent CCSDS Recommendations the quality cannot be determined.
-- If the
--  given service instance does not constrain this parameter to a single value, it shall
--  be flagged 'undefined' whenever si-state ≠ 'active'.
rafRequestedFrameQualityParamOid	 OBJECT IDENTIFIER ::= { 1 3 112 4 4 2 1 80400 1 12 1 1 }

RafRequestedFrameQuality	 ::= ENUMERATED
{
	 good                	 	 (0)
,	 erred               	 	 (1)
,	 all                 	 	 (2)
}



-- This parameter reports if cyclic reporting is active and if so it reports  the current
--  setting of the time in seconds between successive RAF-STATUS-REPORT invocations
--  sent by the RAF service provider. 
rafReportingCycleParamOid	 OBJECT IDENTIFIER ::= { 1 3 112 4 4 2 1 80400 1 13 1 1 }

-- The engineering unit of this parameter is second.
RafReportingCycle   	 ::= SleReportingCycle


-- This parameter reports the  total number of telemetry frames that were annotated
--  with a frame-quality of ‘good’ and delivered to the user since the start of the
--  service instance provision period.
rafNumberOfErrorFreeFramesDeliveredParamOid	 OBJECT IDENTIFIER ::= { 1 3 112 4 4 2 1 80400 1 14 1 1 }

RafNumberOfErrorFreeFramesDelivered	 ::= INTEGER  (0 .. 4294967295)


-- This parameter reports the  total number of telemetry frames that were delivered
--  to the user since the start of the service instance provision period.
rafNumberOfFramesDeliveredParamOid	 OBJECT IDENTIFIER ::= { 1 3 112 4 4 2 1 80400 1 15 1 1 }

RafNumberOfFramesDelivered	 ::= INTEGER  (0 .. 4294967295)


-- This event notifies any change of the rafProductionStat parameter. 
rafProdStatChangeEventOid	 OBJECT IDENTIFIER ::= { 1 3 112 4 4 2 1 80400 2 1 1 }




-- The event value reports the rafProdStat value that applies since the notified rafProdStatChange
--  event occurred.
rafProdStatChangeEventValueValueOid	 OBJECT IDENTIFIER ::= { 1 3 112 4 4 2 1 80400 2 1 1 1 }

RafProdStatChangeEventValue	 ::= RafProdStat


-- This event triggers when a one or more parameters controlling the configuration of
--  service production of the service instance identified by the rafServiceInstanceId
--  parameter have been changed.
-- 
-- This event carries no additional information.
-- 
rafProdConfigurationChangeEventOid	 OBJECT IDENTIFIER ::= { 1 3 112 4 4 2 1 80400 2 2 1 }




-- The event-value of this event is 'empty'.
rafProdConfigurationChangeEventValueValueOid	 OBJECT IDENTIFIER ::= { 1 3 112 4 4 2 1 80400 2 2 1 1 }

RafProdConfigurationChangeEventValue	 ::= ProdConfigurationChangeEventValue


-- This directive permits setting of the controllable parameters of the RafTsProvider
--  FR type. 
rafSetContrParamsDirectiveOid	 OBJECT IDENTIFIER ::= { 1 3 112 4 4 2 1 80400 3 1 1 }




-- The directive qualifier specifies the FR instance the directive shall act on and
--  contains a set of parameter identifier and parameter value pairs. To be valid, the
--  parameter identifier must reference a controllable parameter of the RafTsProvider
--  FR and the parameter value must be of the same type as the parameter value that
--  shall be set.
rafContrParamIdsAndValuesQualifierOid	 OBJECT IDENTIFIER ::= { 1 3 112 4 4 2 1 80400 3 1 1 1 }

RafContrParamIdsAndValues	 ::= DirectiveQualifier


-- The RcfTsProvider accepts as input the frames provided by the FlfSyncAndDecode and
--  the OfflineFrameBuffer FRs. It delivers the frames of the selected Master or Virtual
--  Channel.
rcfTsProviderFrOid	 OBJECT IDENTIFIER ::= { 1 3 112 4 4 2 1 80500 }




-- This enumerated parameter reports the status of the service production process used
--  by the given instance of an RCF service. It can take on the following values:
-- -
--  'running' - the RCF production process is capable of processing a return link Master
--  or Virtual Channel, if available;
-- - 'interrupted' - the RCF production process is
--  stopped due to a fault;
-- - 'halted' - the RCF production process is stopped and production
--  equipment is out of service due to management action.
rcfProdStatParamOid	 OBJECT IDENTIFIER ::= { 1 3 112 4 4 2 1 80500 1 1 1 1 }

RcfProdStat         	 ::= SleRtnProdStat


-- This parameter configures and reports the identifier of the given service instance.
--  
rcfSvcInstanceIdParamOid	 OBJECT IDENTIFIER ::= { 1 3 112 4 4 2 1 80500 1 2 1 1 }

RcfSvcInstanceId    	 ::= SleSvcInstanceId


-- This enumerated parameter reports the status of the given instance of the RCF service.
--  It can take on the following values:
-- - 'unbound' - All resources required to enable
--  the provision of the RCF service have been allocated, and all objects required to
--  provide the service have been instantiated; however, no association yet exists between
--  the user and the provider, i.e., the RCF transfer service provider port is not bound;
-- -
--  'ready'- An association has been established between the user and the provider,
--  and they may interact by means of the service operations. However, sending of telemetry
--  frames from the provider to the user (by means of the RCF-TRANSFER-DATA operation)
--  is not permitted; the user may enable the delivery of telemetry frames by means
--  of the appropriate service operation (RCF-START), which, in turn, will cause the
--  provider to transition to the state 'active';
-- - 'active' -  This state resembles
--  state ‘ready’, except that now the provider will send telemetry frames provided
--  frames of the selected characteristics are made available by the RCF production
--  process; the service continues in this state until the user invokes the RCF-STOP
--  operation to cause the provider to suspend delivery of telemetry frames and transition
--  back to state 'ready' or the PEER-ABORT invocation to cause the service to transition
--  back to the 'unbound' state.
rcfSvcInstanceStateParamOid	 OBJECT IDENTIFIER ::= { 1 3 112 4 4 2 1 80500 1 3 1 1 }

RcfSvcInstanceState 	 ::= SleSvcInstanceState


-- This parameter reports the identifier of the peer application, i.e., the authority
--  on whose behalf the SLE application entity is initiating an association with the
--  RCF service provider. The provider performs access control based on this parameter.
--  It may also serve as key to further security relevant information such as the authentication
--  level and method and the related password.
-- 
-- Given the security relevance of this
--  parameter, specific mechanisms for setting this parameter when the FR instance is
--  created and for the transfer of associated security relevant data might be specified
--  in a bilateral agreement between service user and service provider. Also the accessibility
--  by an MD-CSTS instance may be restricted.
rcfInitiatorIdParamOid	 OBJECT IDENTIFIER ::= { 1 3 112 4 4 2 1 80500 1 4 1 1 }

RcfInitiatorId      	 ::= AuthorityIdentifier


-- This parameter reports the identifier of the RCF application. The user performs access
--  conrol based on this parameter. It may also serve as key to further security relevant
--  information such as the authentication level and method and the related password.
-- 
-- Given
--  the security relevance of this parameter, specific mechanisms for setting this parameter
--  when the FR instance is created and for the transfer of associated security relevant
--  data might be specified in a bilateral agreement between service user and service
--  provider. Also the accessibility by an MD-CSTS instance may be restricted.
rcfResponderIdParamOid	 OBJECT IDENTIFIER ::= { 1 3 112 4 4 2 1 80500 1 5 1 1 }

RcfResponderId      	 ::= AuthorityIdentifier


-- This parameter reports the port identifier to be used by the user to connect to the
--  service provider. However, the parameter value is only a logical name that needs
--  to be translated into the technology-specific addressing information required to
-- establish
--  a connection with the specific port of the
-- responding SLE application entity. As
--  such this parameter is irrelevant for the service provider, but it may be needed
--  for certain kind of gateways between service user and service provider application.
rcfResponderPortIdParamOid	 OBJECT IDENTIFIER ::= { 1 3 112 4 4 2 1 80500 1 6 1 1 }

RcfResponderPortId  	 ::= ResponderPortId


-- This parameter reports the setting of the maximum time period in seconds permitted
--  from when a confirmed RCF operation is invoked until the return is received by the
--  invoker.
-- 
-- If a response is not received within that time period, the invoker may
--  invoke the PEER-ABORT operation.
rcfRtnTimeoutPeriodParamOid	 OBJECT IDENTIFIER ::= { 1 3 112 4 4 2 1 80500 1 7 1 1 }

-- The engineering unit of this parameter is second.
RcfRtnTimeoutPeriod 	 ::= SleRtnTimeout


-- This enumerated parameter configures and reports the delivery mode of the given RCF
--  service instance. It can take on three values:
-- - 'online timely'  - the timely
--  online delivery mode limits the size of the backlog of not yet delivered data that
--  is allowed to accumulate by discarding data that cannot be delivered within a certain
--  time. Furthermore, when data is discarded, it is discarded ‘in
-- chunks’, i.e., as
--  a sufficiently large block of contiguous frames rather than as random frames here
--  and there; in general, this approach maximizes the usefulness of the data that is
--  delivered.
-- - 'online complete' - this delivery mode attempts to deliver all acquired
--  frames having the user selected characteristics, in order, with minimum delay consistent
--  with the available ground communications bandwidth. To that end, the service provider
--  has a buffer sufficiently large to deal with communications service delays, outages,
--  and bandwidth limitations;
-- - 'offline' - in this delivery mode, the provider side
--  buffer enables data to be delivered hours or days after their acquisition. To that
--  end, this buffer is sufficiently large to hold all data that might be accumulated
--  during several space link sessions.
rcfDeliveryModeParamOid	 OBJECT IDENTIFIER ::= { 1 3 112 4 4 2 1 80500 1 8 1 1 }

RcfDeliveryMode     	 ::= SleRtnDeliveryMode


-- This parameter configures and reports the maximum allowable delivery latency time,
--  in seconds, for the online delivery modes, i.e., the maximum delay from when the
--  frame is acquired by the provider until it is delivered to the user. This parameter
--  shall be flagged as undefined if rcfDeliveryMode = 'offline'.
rcfLatencyLimitParamOid	 OBJECT IDENTIFIER ::= { 1 3 112 4 4 2 1 80500 1 9 1 1 }

-- The engineering unit of this parameter is second.
RcfLatencyLimit     	 ::= INTEGER  (1 .. 100)


-- This parameter configures and reports the number of frames the provider shall block
--  in one RCF-PDU before passing it to the underlying communications layer except if
--  expiry of rcfLatencyLimit requires earlier release of the RCF-PDU. If rcfDeliveryMode
--  = 'offline', rcfLatencyLimit has no effect.
rcfTransferBufferSizeParamOid	 OBJECT IDENTIFIER ::= { 1 3 112 4 4 2 1 80500 1 10 1 1 }

RcfTransferBufferSize	 ::= INTEGER  (1 .. 100)


-- This parameter reports the set of Master and/or Virtual Channel that the given RCF
--  service instance permits the user to select. The parameter is a set of the concatenation
--  of the CCSDS assigned Spacecraft Identifier (SCID), the Transfer Frame Version Number
--  (TFVN) and, if applicable, the Virtual Channel Identifier (VCID). The range of the
--  Spacecraft Identifier and the Virtual Channel Identifier depend on the TFVN as follows:
-- -
--  TFVN = 0 (version 1) - SCID = (0 .. 1023)10, VCID = (0 .. 7)10;
-- - TFVN = 1 (version
--  2) - SCID = (0 .. 255)10, VCID = (0 .. 63)10.
rcfPermittedGvcidSetParamOid	 OBJECT IDENTIFIER ::= { 1 3 112 4 4 2 1 80500 1 11 1 1 }

RcfPermittedGvcidSet	 ::= CHOICE
{
	 tm                  	 [0]	 	 SET  (SIZE( 1 .. 9216))  OF	 SEQUENCE
	 	 {

	 	 	 -- The TFVN of Tm frames is always 0.
	 	 	 tfvn                	 INTEGER  (0)
,	 	 	 scid                	 INTEGER  (0 .. 1023)
,	 	 	 vcid                	 CHOICE
	 	 	 {

	 	 	 	 -- For the Master Channel the vcid remains unspecified.
	 	 	 	 masterChannel       	 [0]	 	 NULL
,	 	 	 	 virtualChannel      	 [1]	 	 INTEGER  (0 .. 7)
	 	 	 }

	 	 }

,	 aos                 	 [1]	 	 SET  (SIZE( 1 .. 16640))  OF	 SEQUENCE
	 	 {

	 	 	 -- The TFVN of AOS frames is always 1.
	 	 	 tfvn                	 INTEGER  (1)
,	 	 	 scid                	 INTEGER  (0 .. 255)
,	 	 	 vcid                	 CHOICE
	 	 	 {

	 	 	 	 -- For the Master Channel the vcid remains unspecified.
	 	 	 	 masterChannel       	 [0]	 	 NULL
,	 	 	 	 virtualChannel      	 [1]	 	 INTEGER  (0 .. 63)
	 	 	 }

	 	 }

}



-- This parameter reports the Master or Virtual Channel that the given RCF service instance
--  shall deliver to the user. The parameter is a concatenation of the CCSDS assigned
--  Spacecraft Identifier (SCID), the Transfer Frame Version Number (TFVN) and, if applicable,
--  the Virtual Channel Identifier (VCID). The range of the Spacecraft Identifier and
--  the Virtual Channel Identifier depend on the TFVN as follows:
-- - TFVN = 0 (version
--  1) - SCID = (0 .. 1023)10, VCID = (0 .. 7)10;
-- - TFVN = 1 (version 2) - SCID = (0
--  .. 255)10, VCID = (0 .. 63)10.
-- If the global VCID is not constrained to a single
--  value by the given RCF service instance (see permitted-global-vcid-set), then this
--  parameter shall be flagged undefined as long as si-state ≠ 'active.
rcfRequestedGvcidParamOid	 OBJECT IDENTIFIER ::= { 1 3 112 4 4 2 1 80500 1 12 1 1 }

RcfRequestedGvcid   	 ::= CHOICE
{
	 tm                  	 [0]	 	 SEQUENCE
	 {

	 	 -- The TFVN of TM frames is always 0.
	 	 tfvn                	 INTEGER  (0)
,	 	 scid                	 INTEGER  (0 .. 1023)
,	 	 vcid                	 CHOICE
	 	 {

	 	 	 -- In case the Master Channel is selected, the VCID remains unspecified.
	 	 	 masterChannel       	 [0]	 	 NULL
,	 	 	 vcid                	 [1]	 	 INTEGER  (0 .. 7)
	 	 }

	 }

,
	 -- The TFVN of AOS frames is always 1.
	 aos                 	 [1]	 	 SEQUENCE
	 {

	 	 -- The TFVN of AOS frames is always 1.
	 	 tfvn                	 INTEGER  (1)
,	 	 scid                	 INTEGER  (0 .. 255)
,	 	 vcid                	 CHOICE
	 	 {

	 	 	 -- When a Master Channel is selected, the VCID remains unspecified.
	 	 	 masterChannel       	 [0]	 	 NULL
,	 	 	 virtualChannel      	 [1]	 	 INTEGER  (0 .. 63)
	 	 }

	 }

}



-- This parameter reports if cyclic reporting is active and if so it reports  the current
--  setting of the time in seconds between successive RCF-STATUS-REPORT invocations
--  sent by the RCF service provider. 
rcfReportingCycleParamOid	 OBJECT IDENTIFIER ::= { 1 3 112 4 4 2 1 80500 1 13 1 1 }

RcfReportingCycle   	 ::= SleReportingCycle


-- This parameter reports the total number of telemetry frames that were delivered to
--  the user since the start of the service instance provision period.
rcfNumberOfFramesDeliveredParamOid	 OBJECT IDENTIFIER ::= { 1 3 112 4 4 2 1 80500 1 14 1 1 }

RcfNumberOfFramesDelivered	 ::= INTEGER  (0 .. 4294967295)


-- This event notifies any change of the rcfProductionStat parameter. 
rcfProdStatChangeEventOid	 OBJECT IDENTIFIER ::= { 1 3 112 4 4 2 1 80500 2 1 1 }




-- The event value reports the rcfProdStat value that applies since the notified rcfProdStatChange
--  event occurred.
rcfProdStatChangeEventValueValueOid	 OBJECT IDENTIFIER ::= { 1 3 112 4 4 2 1 80500 2 1 1 1 }

RcfProdStatChangeEventValue	 ::= RcfProdStat


-- This event triggers when a one or more parameters controlling the configuration of
--  service production of the service instance identified by the rcfSvcInstanceId parameter
--  have been changed.
-- 
-- This event carries no additional information.
-- 
rcfProdConfigurationChangeEventOid	 OBJECT IDENTIFIER ::= { 1 3 112 4 4 2 1 80500 2 2 1 }




-- The event-value of this event is 'empty'.
rcfProdConfigurationChangeEventValueValueOid	 OBJECT IDENTIFIER ::= { 1 3 112 4 4 2 1 80500 2 2 1 1 }

RcfProdConfigurationChangeEventValue	 ::= ProdConfigurationChangeEventValue


-- This directive permits setting of the controllable parameters of the RcfTsProvider
--  FR type. 
rcfSetContrParamsDirectiveOid	 OBJECT IDENTIFIER ::= { 1 3 112 4 4 2 1 80500 3 1 1 }




-- The directive qualifier specifies the FR instance the directive shall act on and
--  contains a set of parameter identifier and parameter value pairs. To be valid, the
--  parameter identifier must reference a controllable parameter of the RcfTsProvider
--  FR and the parameter value must be of the same type as the parameter value that
--  shall be set.
rcfContrParamIdsAndValuesQualifierOid	 OBJECT IDENTIFIER ::= { 1 3 112 4 4 2 1 80500 3 1 1 1 }

RcfContrParamIdsAndValues	 ::= DirectiveQualifier


-- The RocfTsProvider accepts as input the frames provided by the FlfSyncAndDecode and
--  the OfflineFrameBuffer FRs. It delivers the Operational Control Fields (OCF) extracted
--  from the frames of the selected Master or Virtual Channel provided the OCFs meet
--  the other selection criteria set by the ROCF service user.
rocfTsProviderFrOid	 OBJECT IDENTIFIER ::= { 1 3 112 4 4 2 1 80600 }




-- This enumerated parameter reports the status of the service production process used
--  by the given instance of an ROCF service. It can take on the following values:
-- -
--  'running' - the ROCF production process is capable of processing a return link Master
--  or Virtual Channel, if available;
-- - 'interrupted' - the ROCF production process
--  is stopped due to a fault;
-- - 'halted' - the ROCF production process is stopped and
--  production equipment is out of service due to management action.
rocfProdStatParamOid	 OBJECT IDENTIFIER ::= { 1 3 112 4 4 2 1 80600 1 1 1 1 }

RocfProdStat        	 ::= SleRtnProdStat


-- This parameter configures and reports the identifier of the given service instance.
--  
rocfSvcInstanceIdParamOid	 OBJECT IDENTIFIER ::= { 1 3 112 4 4 2 1 80600 1 2 1 1 }

RocfSvcInstanceId   	 ::= SleSvcInstanceId


-- This enumerated parameter reports the status of the given instance of the ROCF service.
--  It can take on the following values:
-- - 'unbound' - All resources required to enable
--  the provision of the ROCF service have been allocated, and all objects required
--  to provide the service have been instantiated; however, no association yet exists
--  between the user and the provider, i.e., the ROCF transfer service provider port
--  is not bound;
-- - 'ready'- An association has been established between the user and
--  the provider, and they may interact by means of the service operations. However,
--  sending of Operational Control Fields (OCFs) from the provider to the user (by means
--  of the ROCF-TRANSFER-DATA operation) is not permitted; the user may enable the delivery
--  of OCFs by means of the appropriate service operation (ROCF-START), which, in turn,
--  will cause the provider to transition to the state 'active';
-- - 'active' -  This
--  state resembles state ‘ready’, except that now the provider will send OCFs provided
--  frames of the selected characteristics are made available by the ROCF production
--  process; the service continues in this state until the user invokes the ROCF-STOP
--  operation to cause the provider to suspend delivery of OCFs and transition back
--  to state 'ready or the PEER-ABORT invocation to cause the service to transition
--  back to the 'unbound' state.
rocfSvcInstanceStateParamOid	 OBJECT IDENTIFIER ::= { 1 3 112 4 4 2 1 80600 1 3 1 1 }

RocfSvcInstanceState	 ::= SleSvcInstanceState


-- This parameter reports the identifier of the peer application, i.e., the authority
--  on whose behalf the SLE application entity is initiating an association with the
--  ROCF service provider. The provider performs access control based on this parameter.
--  It may also serve as key to further security relevant information such as the authentication
--  level and method and the related password.
-- 
-- Given the security relevance of this
--  parameter, specific mechanisms for setting this parameter when the FR instance is
--  created and for the transfer of associated security relevant data might be specified
--  in a bilateral agreement between service user and service provider. Also the accessibility
--  by an MD-CSTS instance may be restricted.
rocfInitiatorIdParamOid	 OBJECT IDENTIFIER ::= { 1 3 112 4 4 2 1 80600 1 4 1 1 }

RocfInitiatorId     	 ::= AuthorityIdentifier


-- This parameter reports the identifier of the ROCF application. The user performs
--  access conrol based on this parameter. It may also serve as key to further security
--  relevant information such as the authentication level and method and the related
--  password.
-- 
-- Given the security relevance of this parameter, specific mechanisms
--  for setting this parameter when the FR instance is created and for the transfer
--  of associated security relevant data might be specified in a bilateral agreement
--  between service user and service provider. Also the accessibility by an MD-CSTS
--  instance may be restricted.
rocfResponderIdParamOid	 OBJECT IDENTIFIER ::= { 1 3 112 4 4 2 1 80600 1 5 1 1 }

RocfResponderId     	 ::= AuthorityIdentifier


-- This parameter reports the port identifier to be used by the user to connect to the
--  service provider. However, the parameter value is only a logical name that needs
--  to be translated into the technology-specific addressing information required to
-- establish
--  a connection with the specific port of the
-- responding SLE application entity. As
--  such this parameter is irrelevant for the service provider, but it may be needed
--  for certain kind of gateways between service user and service provider application.
rocfResponderPortIdParamOid	 OBJECT IDENTIFIER ::= { 1 3 112 4 4 2 1 80600 1 6 1 1 }

RocfResponderPortId 	 ::= ResponderPortId


-- This parameter reports the setting of the maximum time period in seconds permitted
--  from when a confirmed ROCF operation is invoked until the return is received by
--  the invoker.
-- 
-- If a response is not received within that time period, the invoker
--  may invoke the PEER-ABORT operation.
rocfRtnTimeoutPeriodParamOid	 OBJECT IDENTIFIER ::= { 1 3 112 4 4 2 1 80600 1 7 1 1 }

-- The engineering unit of this parameter is second
RocfRtnTimeoutPeriod	 ::= SleRtnTimeout


-- This enumerated parameter configures and reports the delivery mode of the given ROCF
--  service instance. It can take on three values:
-- - 'online timely'  - the timely
--  online delivery mode limits the size of the backlog of not yet delivered data that
--  is allowed to accumulate by discarding data that cannot be delivered within a certain
--  time. Furthermore, when data is discarded, it is discarded ‘in
-- chunks’, i.e., as
--  a OCFs extracted from a sufficiently large block of contiguous frames rather than
--  as OCFs from random frames here and there; in general, this approach maximizes the
--  usefulness of the data that is delivered.
-- - 'online complete' - this delivery mode
--  attempts to deliver the OCFs having the user selected characteristics from all acquired
--  frames, in order, with minimum delay consistent with the available ground communications
--  bandwidth. To that end, the service provider has a buffer sufficiently large to
--  deal with communications service delays, outages, and bandwidth limitations;
-- -
--  'offline' - in this delivery mode, the provider side buffer enables data to be delivered
--  hours or days after their acquisition. To that end, this buffer is sufficiently
--  large to hold all data that might be accumulated during several space link sessions.
rocfDeliveryModeParamOid	 OBJECT IDENTIFIER ::= { 1 3 112 4 4 2 1 80600 1 8 1 1 }

RocfDeliveryMode    	 ::= SleRtnDeliveryMode


-- This parameter configures and reports the maximum allowable delivery latency time,
--  in seconds, for the online delivery modes, i.e., the maximum delay from when the
--  provider extracts an OCF from a newly acquired frame until it is delivered to the
--  user. This parameter shall be flagged as undefined if rocfDeliveryMode = 'offline'.
rocfLatencyLimitParamOid	 OBJECT IDENTIFIER ::= { 1 3 112 4 4 2 1 80600 1 9 1 1 }

-- The engineering unit of this parameter is second.
RocfLatencyLimit    	 ::= INTEGER  (1 .. 100)


-- This parameter configures and reports the number of OCFs the provider shall block
--  in one ROCF-PDU before passing it to the underlying communications layer except
--  if expiry of rocfLatencyLimit requires earlier release of the ROCF-PDU. If rocfDeliveryMode
--  = 'offline', rocfLatencyLlimit has no effect.
rocfTransferBufferSizeParamOid	 OBJECT IDENTIFIER ::= { 1 3 112 4 4 2 1 80600 1 10 1 1 }

RocfTransferBufferSize	 ::= INTEGER  (1 .. 100)


-- This parameter reports the telemetry Master and/or Virtual Channel out of which the
--  given ROCF service instance extracts the OCFs. The parameter is a set of the concatenation
--  of the CCSDS assigned Spacecraft Identifier (SCID), the Transfer Frame Version Number
--  (TFVN) and, if applicable, the Virtual Channel Identifier (VCID). The range of the
--  Spacecraft Identifier and the Virtual Channel Identifier depend on the TFVN as follows:
-- -
--  TFVN = 0 (version 1) - SCID = (0 .. 1023)10, VCID = (0 .. 7)10;
-- - TFVN = 1 (version
--  2) - SCID = (0 .. 255)10, VCID = (0 .. 63)10.
rocfPermittedGvcidSetParamOid	 OBJECT IDENTIFIER ::= { 1 3 112 4 4 2 1 80600 1 11 1 1 }

RocfPermittedGvcidSet	 ::= CHOICE
{
	 tm                  	 [0]	 	 SET  (SIZE( 1 .. 9216))  OF	 SEQUENCE
	 	 {

	 	 	 -- The TFVN of Tm frames is always 0.
	 	 	 tfvn                	 INTEGER  (0)
,	 	 	 scid                	 INTEGER  (0 .. 1023)
,	 	 	 vcid                	 CHOICE
	 	 	 {

	 	 	 	 -- For the Master Channel the vcid remains unspecified.
	 	 	 	 masterChannel       	 [0]	 	 NULL
,	 	 	 	 virtualChannel      	 [1]	 	 INTEGER  (0 .. 7)
	 	 	 }

	 	 }

,	 aos                 	 [1]	 	 SET  (SIZE( 1 .. 16640))  OF	 SEQUENCE
	 	 {

	 	 	 -- The TFVN of AOS frames is always 1.
	 	 	 tfvn                	 INTEGER  (1)
,	 	 	 scid                	 INTEGER  (0 .. 255)
,	 	 	 vcid                	 CHOICE
	 	 	 {

	 	 	 	 -- For the Master Channel the vcid remains unspecified.
	 	 	 	 masterChannel       	 [0]	 	 NULL
,	 	 	 	 virtualChannel      	 [1]	 	 INTEGER  (0 .. 63)
	 	 	 }

	 	 }

}



-- This parameter reports the set of Master and/or Virtual Channel that the given ROCF
--  service instance permits the user to select. The parameter is a set of the concatenation
--  of the CCSDS assigned Spacecraft Identifier (SCID), the Transfer Frame Version Number
--  (TFVN) and, if applicable, the Virtual Channel Identifier (VCID). The range of the
--  Spacecraft Identifier and the Virtual Channel Identifier depend on the TFVN as follows:
-- -
--  TFVN = 0 (version 1) - SCID = (0 .. 1023)10, VCID = (0 .. 7)10;
-- - TFVN = 1 (version
--  2) - SCID = (0 .. 255)10, VCID = (0 .. 63)10.
-- If the global VCID is not constrained
--  to a single value by the given ROCF service instance, then this parameter shall
--  be flagged as undefined as long as si-state ≠ 'active.
rocfRequestedGvcidParamOid	 OBJECT IDENTIFIER ::= { 1 3 112 4 4 2 1 80600 1 12 1 1 }

RocfRequestedGvcid  	 ::= CHOICE
{
	 tm                  	 [0]	 	 SEQUENCE
	 {

	 	 -- The TFVN of TM frames is always 0.
	 	 tfvn                	 INTEGER  (0)
,	 	 scid                	 INTEGER  (0 .. 1023)
,	 	 vcid                	 CHOICE
	 	 {

	 	 	 -- In case the Master Channel is selected, the VCID remains unspecified.
	 	 	 masterChannel       	 [0]	 	 NULL
,	 	 	 vcid                	 [1]	 	 INTEGER  (0 .. 7)
	 	 }

	 }

,
	 -- The TFVN of AOS frames is always 1.
	 aos                 	 [1]	 	 SEQUENCE
	 {

	 	 -- The TFVN of AOS frames is always 1.
	 	 tfvn                	 INTEGER  (1)
,	 	 scid                	 INTEGER  (0 .. 255)
,	 	 vcid                	 CHOICE
	 	 {

	 	 	 -- When a Master Channel is selected, the VCID remains unspecified.
	 	 	 masterChannel       	 [0]	 	 NULL
,	 	 	 virtualChannel      	 [1]	 	 INTEGER  (0 .. 63)
	 	 }

	 }

}



-- This parameter reports the set of OCF types that the given ROCF service instance
--  permits the user to select. Three types are defined:
-- - 'all control word types'
--  - all OCFs shall be delivered regardless of their type;
-- - 'clcws only' - only OCFs
--  containing the CCSDS defined Communication Link Control Word (CLCW) data structure
--  shall be delivered;
-- - 'non-clcws only' - only privately defined OCFs shall be delivered.
--    
rocfPermittedContrWordTypeSetParamOid	 OBJECT IDENTIFIER ::= { 1 3 112 4 4 2 1 80600 1 13 1 1 }

RocfPermittedContrWordTypeSet	 ::= SET  (SIZE( 1 .. 3))  OF	 ENUMERATED
	 {
	 	 allControlWordTypes 	 	 (0)
	 ,	 clcwsOnly           	 	 (1)
	 ,	 nonClcwsOnly        	 	 (2)
	 }



-- This enumerated parameter reports the type of the OCFs that shall be delivered. It
--  can take on three values:
-- - all control word types' - the service provider delivers
--  all OCFs extracted from the selected telemetry channel, regardless of the control
--  word type they contain;
-- - 'clcws only' - the service provider delivers the OCFs
--  extracted from the selected telemetry channel that contain CLCW reports;
-- - 'non-clcws
--  only' - the service provider delivers the OCFs extracted from the selected telemetry
--  channel that contain reports different from CLCWs.
rocfRequestedContrWordTypeParamOid	 OBJECT IDENTIFIER ::= { 1 3 112 4 4 2 1 80600 1 14 1 1 }

RocfRequestedContrWordType	 ::= ENUMERATED
{
	 allControlWordTypes 	 	 (0)
,	 clcwsOnly           	 	 (1)
,	 nonClcwsOnly        	 	 (2)
}



-- This parameter reports the TC Master Channel and/or the Virtual Channels that the
--  CLCWs that shall be extracted are associated with. If rocfRequestedContrWordType
--  ≠ 'clcw', this parameter shall be flagged as undefined. 
rocfPermittedTcVcidSetParamOid	 OBJECT IDENTIFIER ::= { 1 3 112 4 4 2 1 80600 1 15 1 1 }

RocfPermittedTcVcidSet	 ::= SET  (SIZE( 1 .. 66560))  OF	 SEQUENCE
	 {

	 	 -- The TFVN of TC frames is always 0.
	 	 tfvn                	 INTEGER  (0)
,	 	 scid                	 INTEGER  (0 .. 1023)
,	 	 vcid                	 CHOICE
	 	 {

	 	 	 -- When the Master Channel is selected, the VCID remains unspecified.
	 	 	 masterChannel       	 [0]	 	 NULL
,	 	 	 vcid                	 [1]	 	 INTEGER  (0 .. 63)
	 	 }

	 }



-- This parameter reports which TC Master Channel or Virtual Channel the OCFs to be
--  delivered shall be associated with. The parameter is a concatenation of the CCSDS
--  assigned Spacecraft Identifier (SCID), the Transfer Frame Version Number (TFVN)
--  and, if applicable, the Virtual Channel Identifier (VCID).
-- If rocfRequestedContrWordType
--  ≠ 'clcws only', this parameter shall be flagged as undefined.
rocfRequestedTcVcidParamOid	 OBJECT IDENTIFIER ::= { 1 3 112 4 4 2 1 80600 1 16 1 1 }

RocfRequestedTcVcid 	 ::= SEQUENCE
{

	 -- The TFVN of TC frames is always 0.
	 tfvn                	 INTEGER  (0)
,	 scid                	 INTEGER  (0 .. 1023)
,	 vcid                	 CHOICE
	 {

	 	 -- When the Master Channel is selected, the VCID remains unspecified.
	 	 masterChannel       	 [0]	 	 NULL
,	 	 vcid                	 [1]	 	 INTEGER  (0 .. 63)
	 }

}



-- This parameter reports the update modes that the given ROCF service instance permits.
--  The update modes are:
-- - 'continuous': the given ROCF service permits the 'continuous'
--  mode, i.e. the OCF service provider delivers each OCF that fulfills the delivery
--  criteria specified by the ROCF-START invocation parameters start-time, stop-time,
--  requested-global-VCID, control-word-type, and tc-vcid;
-- - 'onChange': the ROCF service
--  provider delivers those OCFs that fulfill the delivery criteria specified by the
--  ROCF-START invocation parameters start-time, stop-time, requested-global-VCID, control-word-type,
--  and tc-vcid provided the content of the OCF is different than the one of the OCF
--  with the same tc-vcid value previously delivered. 
rocfPermittedUpdateModeParamOid	 OBJECT IDENTIFIER ::= { 1 3 112 4 4 2 1 80600 1 17 1 1 }

RocfPermittedUpdateMode	 ::= SET  (SIZE( 1 .. 2))  OF	 ENUMERATED
	 {
	 	 continuous          	 	 (0)
	 ,	 onChange            	 	 (1)
	 }



-- This enumerated parameter reports the update mode applied by the ROCF service provider
--  for the delivery of OCFs. It can take on two values:
-- - 'continuous' - the ROCF
--  service provider delivers each OCF that fulfills the delivery criteria specified
--  by the ROCF-START invocation parameters start-time, stop-time, requested-global-VCID,
--  control-word-type, and tc-vcid;
-- - 'onChange' - the ROCF service provider delivers
--  those OCFs that fulfill the delivery criteria specified by the ROCF-START invocation
--  parameters start-time, stop-time, requested-global-VCID, control-word-type, and
--  tc-vcid provided the content of the OCF is different than the one of the OCF with
--  the same tc-vcid value previously delivered. 
rocfRequestedUpdateModeParamOid	 OBJECT IDENTIFIER ::= { 1 3 112 4 4 2 1 80600 1 18 1 1 }

RocfRequestedUpdateMode	 ::= ENUMERATED
{
	 continuous          	 	 (0)
,	 onChange            	 	 (1)
}



-- This parameter reports if cyclic reporting is active and if so it reports  the current
--  setting of the time in seconds between successive ROCF-STATUS-REPORT invocations
--  sent by the ROCF service provider. 
rocfReportingCycleParamOid	 OBJECT IDENTIFIER ::= { 1 3 112 4 4 2 1 80600 1 19 1 1 }

RocfReportingCycle  	 ::= SleReportingCycle


-- This parameter reports the  total number of OCFs that were delivered to the user
--  since the start of the service instance provision period.
rocfNumberOfOcfsDeliveredParamOid	 OBJECT IDENTIFIER ::= { 1 3 112 4 4 2 1 80600 1 20 1 1 }

RocfNumberOfOcfsDelivered	 ::= INTEGER  (0 .. 4294967295)


-- This event notifies any change of the rocfProductionStat parameter. 
rocfProdStatChangeEventOid	 OBJECT IDENTIFIER ::= { 1 3 112 4 4 2 1 80600 2 1 1 }




-- The event value reports the rocfProdStat value that applies since the notified rocfProdStatChange
--  event occurred.
rocfProdStatChangeEventValueValueOid	 OBJECT IDENTIFIER ::= { 1 3 112 4 4 2 1 80600 2 1 1 1 }

RocfProdStatChangeEventValue	 ::= RocfProdStat


-- This event triggers when a one or more parameters controlling the configuration of
--  service production of the service instance identified by the rocfServiceInstanceId
--  parameter have been changed.
-- 
-- This event carries no additional information.
-- 
rocfProdConfigurationChangeEventOid	 OBJECT IDENTIFIER ::= { 1 3 112 4 4 2 1 80600 2 2 1 }




-- The event-value of this event is 'empty'.
rocfProdConfigurationChangeEventValueValueOid	 OBJECT IDENTIFIER ::= { 1 3 112 4 4 2 1 80600 2 2 1 1 }

RocfProdConfigurationChangeEventValue	 ::= ProdConfigurationChangeEventValue


-- This directive permits setting of the controllable parameters of the RocfTsProvider
--  FR type. 
rocfSetContrParamsDirectiveOid	 OBJECT IDENTIFIER ::= { 1 3 112 4 4 2 1 80600 3 1 1 }




-- The directive qualifier specifies the FR instance the directive shall act on and
--  contains a set of parameter identifier and parameter value pairs. To be valid, the
--  parameter identifier must reference a controllable parameter of the RocfTsProvider
--  FR and the parameter value must be of the same type as the parameter value that
--  shall be set.
rocfContrParamIdsAndValuesQualifierOid	 OBJECT IDENTIFIER ::= { 1 3 112 4 4 2 1 80600 3 1 1 1 }

RocfContrParamIdsAndValues	 ::= DirectiveQualifier


-- none
tdCstsProviderFrOid	 OBJECT IDENTIFIER ::= { 1 3 112 4 4 2 1 80700 }



tdProdStatParamOid	 OBJECT IDENTIFIER ::= { 1 3 112 4 4 2 1 80700 1 1 1 1 }

TdProdStat          	 ::= ProdStatV1


-- This parameter configures and reports the identifier of the given service instance.
--  
tdSvcInstanceIdParamOid	 OBJECT IDENTIFIER ::= { 1 3 112 4 4 2 1 80700 1 2 1 1 }

TdSvcInstanceId     	 ::= CstsSvcInstanceId

tdSvcInstanceStateParamOid	 OBJECT IDENTIFIER ::= { 1 3 112 4 4 2 1 80700 1 3 1 1 }

TdSvcInstanceState  	 ::= StatefulCstsInstanceState

tdInitiatorIdParamOid	 OBJECT IDENTIFIER ::= { 1 3 112 4 4 2 1 80700 1 4 1 1 }

TdInitiatorId       	 ::= AuthorityIdentifier

tdResponderIdParamOid	 OBJECT IDENTIFIER ::= { 1 3 112 4 4 2 1 80700 1 5 1 1 }

TdResponderId       	 ::= AuthorityIdentifier

tdResponderPortIdParamOid	 OBJECT IDENTIFIER ::= { 1 3 112 4 4 2 1 80700 1 6 1 1 }

TdResponderPortId   	 ::= ResponderPortId


-- This parameter configures and reports the time (in seconds) that the service user
--  should wait before invoking a PEER-ABORT when a return has not been received in
--  response to a BIND or UNBIND invocation.
tdSvcUserRespTimerParamOid	 OBJECT IDENTIFIER ::= { 1 3 112 4 4 2 1 80700 1 7 1 1 }

TdSvcUserRespTimer  	 ::= SvcUserRespTimer


-- This parameter configures and reports the data delivery mode of the Buffered Tracking
--  Data Message Delivery procedure instance. See "Cross Support Transfer Service -
--  Tracking Data Service", CCSDS 922.2.
tdDeliveryModeParamOid	 OBJECT IDENTIFIER ::= { 1 3 112 4 4 2 1 80700 1 8 1 1 }

TdDeliveryMode      	 ::= ENUMERATED
{
	 realtime            	 	 (0)
,	 complete            	 	 (1)
}



-- This parameter configures and reports the return buffer size (in TRANSFER-DATA and/or
--  NOTIFY invocations) to be used by the Buffered Tracking Data Message Delivery procedure
--  instance. See "Cross Support Transfer Service - Tracking Data Service", CCSDS 922.2.
tdReturnBufferSizeParamOid	 OBJECT IDENTIFIER ::= { 1 3 112 4 4 2 1 80700 1 9 1 1 }

TdReturnBufferSize  	 ::= LongIntPos


-- This parameter configures and reports the delivery latency limit (in seconds) to
--  be used by the Buffered Tracking Data Message Delivery procedure instance. See "Cross
--  Support Transfer Service - Tracking Data Service", CCSDS 922.2.
tdDeliveryLatencyLimitParamOid	 OBJECT IDENTIFIER ::= { 1 3 112 4 4 2 1 80700 1 10 1 1 }

TdDeliveryLatencyLimit	 ::= ShortIntPos


-- This parameter configures and reports the set of named label lists to be used by
--  the Information Query procedure instance. See "Cross Support Transfer Service -
--  Tracking Data Service", CCSDS 922.2.
tdNamedLabelListsParamOid	 OBJECT IDENTIFIER ::= { 1 3 112 4 4 2 1 80700 1 11 1 1 }

-- the values of the paramOrEventId components are constrained to be parameter identifiers
TdNamedLabelLists   	 ::= LabelListSetV1


-- This parameter configures and reports the list of trackingDataPathIds for which this
--  TD service instance will report the TDM Atomic Segments. See the TdmSegmentGen FR.
tdPathListParamOid	 OBJECT IDENTIFIER ::= { 1 3 112 4 4 2 1 80700 1 12 1 1 }

TdPathList          	 ::= SEQUENCE  OF	 VisibleString


-- This event notifies any change of the rocfProdStat parameter. 
tdProdStatChangeEventOid	 OBJECT IDENTIFIER ::= { 1 3 112 4 4 2 1 80700 2 1 1 }




-- The event value reports the tdProdStat value that applies since the notified tdProdStatChange
--  event occurred.
tdProdStatChangeEventValueValueOid	 OBJECT IDENTIFIER ::= { 1 3 112 4 4 2 1 80700 2 1 1 1 }

TdProdStatChangeEventValue	 ::= TdProdStat


-- This event triggers when a one or more parameters controlling the configuration of
--  service production of the service instance identified by the tdSvcInstanceId parameter
--  have been changed.
-- 
-- This event carries no additional information.
-- 
tdProdConfigurationChangeEventOid	 OBJECT IDENTIFIER ::= { 1 3 112 4 4 2 1 80700 2 2 1 }




-- The event-value of this event is 'empty'.
tdProdConfigurationChangeEventValueValueOid	 OBJECT IDENTIFIER ::= { 1 3 112 4 4 2 1 80700 2 2 1 1 }

TdProdConfigurationChangeEventValue	 ::= ProdConfigurationChangeEventValue


-- This directive permits setting of the controllable parameters of the TdCstsProvider
--  FR type. 
tdSetContrParamsDirectiveOid	 OBJECT IDENTIFIER ::= { 1 3 112 4 4 2 1 80700 3 1 1 }




-- The directive qualifier specifies the FR instance the directive shall act on and
--  contains a set of parameter identifier and parameter value pairs. To be valid, the
--  parameter identifier must reference a controllable parameter of the TdCstsProvider
--  FR and the parameter value must be of the same type as the parameter value that
--  shall be set.
tdContrParamIdsAndValuesQualifierOid	 OBJECT IDENTIFIER ::= { 1 3 112 4 4 2 1 80700 3 1 1 1 }

TdContrParamIdsAndValues	 ::= DirectiveQualifier


-- none
tgftHostFrOid	 OBJECT IDENTIFIER ::= { 1 3 112 4 4 2 1 80800 }




-- The MonitoredDataCSTSProvider FR has read-access to all parameters and is capable
--  of being notified of all events of all functional resource instances that are executing
--  within the same Service Package that contains the Monitored Data service instance.
--  The Monitored Data CSTS Provider FR corresponds to the functions specified in the
--  Monitored CSTS Recommended Standard
mdCstsProviderFrOid	 OBJECT IDENTIFIER ::= { 1 3 112 4 4 2 1 90100 }




-- This parameter reports the production status of the Monitored Data service instance.
--  This parameter can take on one of four values:
--  - 'configured': all production
--  functions needed to support this service instance have been configured ;
--  - ‘operational’:
--  all production functions have been enabled to process data for this service instance;
-- 
--  - ‘interrupted’: one or more production functions have been stopped because of an
--  error condition that may be temporary;
--  - ‘halted’: one or more production functions
--  have been stopped by management action.
mdSvcProdStatParamOid	 OBJECT IDENTIFIER ::= { 1 3 112 4 4 2 1 90100 1 1 1 1 }

MdSvcProdStat       	 ::= ProdStatV1


-- This parameter configures and reports the service instance identifier used in the
--  PDUs exchanged between the user and provider of the Monitored Data service instance.
--  
mdSvcInstanceIdParamOid	 OBJECT IDENTIFIER ::= { 1 3 112 4 4 2 1 90100 1 2 1 1 }

MdSvcInstanceId     	 ::= CstsSvcInstanceId


-- This enumerated parameter reports the status of the given instance of the Monitored
--  Data service. It can take on the following values:
--  - 'unbound': all resources
--  required to enable the provision of the service have been allocated, and all objects
--  required to provide the service have been instantiated; However, no association
--  yet exists between the user and the provider, i.e., the transfer service provider
--  port is not bound;
--  - 'boundReady': an association has been established between
--  the user and the provider, and they may interact by means of the service operations.
--  The user may invoke the GET invocation of the Information Query procedure and receive
--  the requested parameter values. The user may activate instances of the Notification
--  procedure and receive event notifications. The user may activate secondary instances
--  of the On-Change-Option Cyclic Report procedure and receive periodic reports of
--  the values of the parameterrs associated with those secondary procedure instances.
--  The user may activate the prime instance of the On-Change-Option Cyclic Report procedure,
--  which causes the provider to transition to the state 'active';
--  - 'boundActive':
--  this state resembles state ‘boundReady’, except that in addition the user also receives
--  periodic reports of the values of the parameters associated with the prime On-Change-Option
--  Cyclic Report  procedure instance. The service instance remains in the 'boundActive'
--  state until the user either invokes (a) the STOP operation of the prime On-Change-Option
--  Cyclic Report  procedure instance to cause the provider to cease sending periodic
--  reports of the values of the parameters associated with the prime On-Change-Option
--  Cyclic Report  procedure instance and transition back to state 'boundReady' or (b)
--  the PEER-ABORT invocation to cause the service to transition back to the 'unbound'
--  state.
mdSvcInstanceStateParamOid	 OBJECT IDENTIFIER ::= { 1 3 112 4 4 2 1 90100 1 3 1 1 }

MdSvcInstanceState  	 ::= StatefulCstsInstanceState


-- This parameter reports the identifier of the peer application, i.e., the authority
--  on whose behalf the CSTS application entity is initiating an association with the
--  Monitored Data service provider. The provider performs access control based on this
--  parameter. It may also serve as key to further security relevant information such
--  as the authentication level and method and the related password.
-- 
-- Given the security
--  relevance of this parameter, specific mechanisms for setting this parameter when
--  the FR instance is created and for the transfer of associated security relevant
--  data might be specified in a bilateral agreement between service user and service
--  provider. 
mdInitiatorIdParamOid	 OBJECT IDENTIFIER ::= { 1 3 112 4 4 2 1 90100 1 4 1 1 }

MdInitiatorId       	 ::= AuthorityIdentifier


-- This parameter reports the identifier of the Monitored Data service application.
--  The user performs access conrol based on this parameter. It may also serve as key
--  to further security relevant information such as the authentication level and method
--  and the related password.
-- 
-- Given the security relevance of this parameter, specific
--  mechanisms for setting this parameter when the FR instance is created and for the
--  transfer of associated security relevant data might be specified in a bilateral
--  agreement between service user and service provider. 
mdResponderIdParamOid	 OBJECT IDENTIFIER ::= { 1 3 112 4 4 2 1 90100 1 5 1 1 }

MdResponderId       	 ::= AuthorityIdentifier


-- This parameter configures and reports the logical name of the port used by the underlying
--  communication service to respond to invocation on this service instance. The logical
--  name is translated internally by the service provider to a port identifier that
--  is appropriate to the underlying communication service.
-- 
-- This parameter configures
--  and reports the port identifier to be used by the user to connect to the service
--  provider. However, the parameter value is only a logical name that needs to be translated
--  into the technology-specific addressing information required to establish a connection
--  with the specific port of the responding CSTS application entity. As such this parameter
--  is irrelevant for the service provider, but it may be needed for certain kind of
--  gateways between service user and service provider application.
mdResponderPortIdParamOid	 OBJECT IDENTIFIER ::= { 1 3 112 4 4 2 1 90100 1 6 1 1 }

MdResponderPortId   	 ::= ResponderPortId


-- This parameter configures and reports the time (in seconds) that the service user
--  should wait before invoking a PEER-ABORT when a return has not been received in
--  response to a BIND or UNBIND invocation.
mdServiceUserRespondingTimerParamOid	 OBJECT IDENTIFIER ::= { 1 3 112 4 4 2 1 90100 1 7 1 1 }

MdServiceUserRespondingTimer	 ::= SvcUserRespTimer


-- This parameter configures and reports the minimum allowed delivery cycle of the On-Change-Option
--  Cyclic Report procedure instance.
mdMinAllowedDeliveryCycleParamOid	 OBJECT IDENTIFIER ::= { 1 3 112 4 4 2 1 90100 1 8 1 1 }

MdMinAllowedDeliveryCycle	 ::= MinAllowedDeliveryCycle


-- This parameter configures and reports the set of named label lists to be used by
--  the On-Change-Option Cyclic Report procedure instance(s) and the Information Query
--  procedure instance. 
mdNamedParamLabelListsParamOid	 OBJECT IDENTIFIER ::= { 1 3 112 4 4 2 1 90100 1 9 1 1 }

-- the values of the paramOrEventId components are constrained to be parameter identifiers
MdNamedParamLabelLists	 ::= LabelListSetV1


-- This parameter configures and reports the set of named event lists to be used by
--  the Notification procedure.
mdNamedEventLabelListsParamOid	 OBJECT IDENTIFIER ::= { 1 3 112 4 4 2 1 90100 1 10 1 1 }

-- The values of the paramOrEventId components are constrained to be event identifiers
MdNamedEventLabelLists	 ::= LabelListSetV1


-- This event notifies that the valiue of mdSvcProdStat has changed.
mdSvcProdStatChangeEventOid	 OBJECT IDENTIFIER ::= { 1 3 112 4 4 2 1 90100 2 1 1 }




-- This event carries the new value of the production status following the change:
-- 
--  - 'configured': all production functions needed to support this service instance
--  are configured ;
--  - ‘operational’: all production functions have been enabled to
--  process data for this service instance;
--  - ‘interrupted’: one or more production
--  functions have been stopped because of an error condition that may be temporary;
-- 
--  - ‘halted’: one or more production functions have been stopped by management action.
mdSvcProdStatChangeValueValueOid	 OBJECT IDENTIFIER ::= { 1 3 112 4 4 2 1 90100 2 1 1 1 }

MdSvcProdStatChangeValue	 ::= ProdStatV1


-- This event triggers when a one or more parameters controlling the configuration of
--  service production have been changed.
-- 
-- This event carries no additional information.
mdSvcProdConfgurationChangeEventOid	 OBJECT IDENTIFIER ::= { 1 3 112 4 4 2 1 90100 2 2 1 }




-- The value of this event is 'empty'
mdSvcProdConfgurationChangeValueValueOid	 OBJECT IDENTIFIER ::= { 1 3 112 4 4 2 1 90100 2 2 1 1 }

MdSvcProdConfgurationChangeValue	 ::= ProdConfigurationChangeEventValue


-- none
scCstsProviderFrOid	 OBJECT IDENTIFIER ::= { 1 3 112 4 4 2 1 90200 }




-- none
scProductionFrOid	 OBJECT IDENTIFIER ::= { 1 3 112 4 4 2 1 90201 }



END
