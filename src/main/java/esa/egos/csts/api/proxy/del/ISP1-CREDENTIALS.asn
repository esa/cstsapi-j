ISP1-CREDENTIALS
-- @(#) ASN.1 Syntax File ISP-CREDENTIALS.asn 1.1
DEFINITIONS
IMPLICIT TAGS
::= BEGIN

ISP1Credentials  ::= SEQUENCE
{ time         OCTET STRING (SIZE(8)) -- CCSDS CDS time code
, randomNumber INTEGER
, theProtected OCTET STRING (SIZE(20..32))
}

END
