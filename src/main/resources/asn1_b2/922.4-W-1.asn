CCSDS-CSTS-RTN-CFDP-PDU-OBJECT-IDENTIFIERS
{	iso(1) identified-organization(3) standards-producing-organization(112) ccsds(4) css(4) csts(1) services(2) rtnCfdpPduService(4)
	rtnCfdpPduServiceModules(4)	object-identifiers(1) version(1)
}

DEFINITIONS
 
IMPLICIT TAGS
::= BEGIN

EXPORTS	rtnCfdpPduBuffDelExtendedOpsParam
,			rtnCfdpPduBuffDelExtendedProcParam
,			rtnCfdpPduDerivedServices
,			rtnCfdpPduExtendedServiceParameters
,			rtnCfdpPduServiceProcedures
;

IMPORTS	services
,			crossSupportFunctionalities
	FROM CCSDS-CSTS-OBJECT-IDENTIFIERS-VERSION2

			BufferSize
	FROM CCSDS-CSTS-COMMON-TYPES-VERSION2
;

-- The CCSDS-CSTS-OBJECT-IDENTIFIERS-VERSION2 and CCSDS-CSTS-COMMON-TYPES-VERSION2 modules
-- are defined in F4.1 and F4.3 of reference [1].

-- **********************************************************
-- Root Object Identifiers of the Service

rtnCfdpPduService	OBJECT IDENTIFIER	::= {services 4}
rtnCfdpPduDerivedServices	OBJECT IDENTIFIER	::=
															{rtnCfdpPduService 1}
rtnCfdpPduExtendedServiceParameters OBJECT IDENTIFIER ::=
{rtnCfdpPduService 2}
rtnCfdpPduServiceProcedures	OBJECT IDENTIFIER	::=
																{rtnCfdpPduService 3}
rtnCfdpPduServiceModules	OBJECT IDENTIFIER	::= {rtnCfdpPduService 4}

-- **********************************************************
-- Procedure Type Identifier:
rtnCfdpPduBuffDel 	OBJECT IDENTIFIER	::= 
                                		{rtnCfdpPduServiceProcedures 1}

rtnCfdpPduBuffDelExtendedOpsParam	OBJECT IDENTIFIER	::=
												 {rtnCfdpPduBuffDel	1}
rtnCfdpPduBuffDelExtendedProcParam	OBJECT IDENTIFIER	::=
												 {rtnCfdpPduBuffDel	2}
rtnCfdpPduBuffDelEventsId				OBJECT IDENTIFIER	::=
												 {rtnCfdpPduBuffDel	3}
rtnCfdpPduBuffDelDirectivesId			OBJECT IDENTIFIER	::=
												 {rtnCfdpPduBuffDel	4}

-- **********************************************************
-- Root Object Identifiers of the RCFDP-CSTS Provider Functional
-- Resource Type

-- The Object Identifiers of the RCFDP-CSTS Provider FR type are specified and
-- registered in the SANA Functional Resources registry (reference [5]) 
-- under the crossSupportFunctionalities subtree. The root of the RCFDP-CSTS
-- Provider FR type OID has the classifier cfdpPduCstsProvider.
-- All parameters of the RCFDP-CSTS Provider FR shall be registered under the
-- node of the cfdpPduCstsProvider subtree that has the OID {cfdpPduCstsProvider 1}.
-- All events of the RCFDP-CSTS Provider FR shall be registered under the
-- node of the cfdpPduCstsProvider subtree that has the OID {cfdpPduCstsProvider 2}.
-- All directives of the RCFDP-CSTS Provider FR shall be registered under the
-- node of the cfdpPduCstsProvider subtree that has the OID {cfdpPduCstsProvider 3}.


END

CCSDS-CSTS-RTN-CFDP-PDU-BUFFERED-DELIVERY-PDUS
{	iso(1) identified-organization(3) standards-producing-organization(112)  ccsds(4) css(4) csts(1) services(2) rtnCfdpPduService(2)   rtnCfdpPduServiceModules(4) extensions(2) rtnCfdpPduBuffDelPdus(1)
	version(1)
}

DEFINITIONS
IMPLICIT TAGS
::= BEGIN

EXPORTS	CfdpDeliveryPdu
;

IMPORTS	BufferedDataDeliveryPdu
   FROM CCSDS-CSTS-BUFFERED-DATA-DELIVERY-PDUS
-- CCSDS-CSTS-BUFFERED-DATA-DELIVERY-PDUS is defined in F4.7 of reference
-- [1]).
			Extended
	FROM CCSDS-CSTS-COMMON-TYPES-VERSION2
			rtnCfdpPduBuffDelExtendedOpsParam
	FROM CCSDS-CSTS-RTN-CFDP-PDU-OBJECT-IDENTIFIERS
;

-- =============================================================
-- The CFDP PDU Delivery procedure is derived from
-- the Buffered Data Delivery procedure. It reuses the PDU defined in the
-- Buffered Data Delivery procedure: BufferedDataDeliveryPdu type defined
-- in the CCSDS-CSTS-BUFFERED-DATA-DELIVERY-PDUS module in F4.7 of
-- reference [1].

CfdpDeliveryPdu  ::=  BufferedDataDeliveryPdu

CfdpDeliveryPduData ::= SEQUENCE OF OCTET STRING

cfdpDeliveryPduDataId OBJECT IDENTIFIER ::=
						{rtnCfdpPduBuffDelExtendedOpsParam	1}



-- START negative return extension parameters
-- No extension parameters are added to the START negative return of the
-- BufferedDataDelivery procedure. Therefore ‘StartReturn’:
-- ‘StandardReturnHeader’: ‘result’: ‘negative’: ‘negExtension’ (refer to
-- the CCSDS-CSTS-COMMON-OPERATIONS-PDUS module in F4.4 of reference [1])
-- shall be set to ‘notUsed’.

-- START negative return extension diagnostics
-- No extension diagnostics are added to the START negative return of the
-- BufferedDataDelivery procedure. Therefore the negative StartReturn is
-- returned using one of the common diagnostics of ‘StandardReturnHeader’:
-- ‘result’: ‘negative’: ‘diagnostic’: ‘Diagnostic’ (refer to 3.3.2.7 of
-- reference [1]) or one of the additional diagnostics defined by
-- ‘StartReturn’: ‘StandardReturnHeader’: ‘result’: ‘negative’:
-- ‘diagnostic’: ‘Diagnostic’: ‘diagnosticExtension’:
-- ‘startDiagnosticExt’: ‘StartDiagnosticExt’ or any of the additional
-- values defined by ‘StartReturn’: ‘StandardReturnHeader’: ‘result’:
-- ‘negative’: ‘diagnostic’: ‘Diagnostic’: ‘diagnosticExtension’:
-- ‘startDiagnosticExt’: ‘StartDiagnosticExt’:
-- ‘startDiagnosticExtExtension’: ‘bddStartDiagExt’:
-- ‘BuffDataDelStartDiagnosticExt’ except
-- buffDataDelStartDiagnosticExtExtension.

-- *****
-- STOP Invocation extension parameters
-- No extension parameters are added to the STOP Invocation of the
-- BufferedDataDelivery procedure. Therefore ‘StopInvocation’:
-- ‘stopInvocationExtension’(refer to the CCSDS-CSTS-COMMON-OPERATIONS-PDUS
-- module in F4.4 of reference [1]) shall be set to ‘notUsed’.

-- STOP positive return extension parameters
-- No extension parameters are added to the STOP positive return of the
-- BufferedDataDelivery procedure. Therefore ‘StopReturn’:
-- ‘StandardReturnHeader’: ‘result’: ‘positive’ (refer to the
-- CCSDS-CSTS-COMMON-OPERATIONS-PDUS module in F4.4 of reference [1]) shall
-- be set to ‘notUsed’.

-- STOP negative return extension parameters
-- No extension parameters are added to the STOP negative return of the
-- BufferedDataDelivery procedure. Therefore ‘StopReturn’:
-- ‘StandardReturnHeader’: ‘result’: ‘negative’: ‘negExtension’ (refer to
-- the CCSDS-CSTS-COMMON-OPERATIONS-PDUS module in F4.4 of reference [1])
-- shall be set to ‘notUsed’.

-- STOP negative return extension diagnostics
-- The negative StopReturn is returned using one of the common diagnostics
-- of ‘StandardReturnHeader’: ‘result’: ‘negative’: ‘diagnostic’:
-- ‘Diagnostic’ (refer to 3.3.2.7 of reference [1]). No additional
-- diagnostics are specified, i.e., ‘StopReturn’: ‘StandardReturnHeader’:
-- ‘result’: ‘negative’: ‘diagnostic’: ‘Diagnostic’ must not be set to
-- ‘diagnosticExtension’.

-- *****
-- TRANSFER-DATA Invocation extension parameters
-- No extension parameters are added to the TRANSFER-DATA Invocation of the
-- BufferedDataDelivery procedure. Therefore ‘TransferDataInvocation’:
-- transferDataInvocationExtension (refer to the
-- CCSDS-CSTS-COMMON- OPERATIONS-PDUS module in F4.4 of reference [1])
-- shall be set to ‘notUsed’.

-- TRANSFER-DATA Invocation data parameter resolution
-- The data parameter of the TRANSFER-DATA Invocation is resolved as an
-- octet string. Therefore ‘TransferDataInvocation’: data’:
-- ‘AbstractChoice’ (refer to the CCSDS-CSTS-COMMON-OPERATIONS-PDUS module
-- in F4.4 of reference [1]) shall be set to ‘opaqueString’.

-- *****
-- NOTIFY Invocation extension
-- No extension parameters are added to the NOTIFY Invocation of the
-- BufferedDataDelivery. Therefore ‘NotifyInvocation’:
-- ‘notifyInvocationExtension’ (refer to the
-- CCSDS-CSTS-COMMON-OPERATIONS-PDUS module in F4.4 of reference [1]) shall
-- be set to ‘notUsed’.

END

CCSDS-CSTS-RTN-CFDP-PDU-SERVICE-PROCEDURE-PARAMETERS-EVENTS-DIRECTIVES
{	iso(1) identified-organization(3) standards-producing-organization(112)  ccsds(4) css(4) csts(1) services(2) serviceIdentifiers(2)    rtnCfdpPduService(4) rtnCfdpPduServiceModules(4)    procedureParamEventDirective(3) version(1)
}

DEFINITIONS
IMPLICIT TAGS
::=	BEGIN

IMPORTS	rtnCfdpPduBuffDelExtendedProcParam
FROM CCSDS-CSTS-RTN-CFDP-PDU-OBJECT-IDENTIFIERS
;

-- ============================================================ 
-- CFDP PDU Delivery

pCFDPPDcfdpPduOperationMode	OBJECT IDENTIFIER ::= 
                				{rtnCfdpPduBuffDelExtendedProcParam	1}

PCFDPPDcfdpPduOperationModeType ::= ENUMERATED
{
	fullCfdpData		(0)
,	reducedCfdpData	(1)
}

pCFDPPDcfdpDestEntities	OBJECT IDENTIFIER ::= 
                				{rtnCfdpPduBuffDelExtendedProcParam	2}

PCFDPPDcfdpDestEntitiesType ::= SEQUENCE OF INTEGER

-- CFDP PDU Aggregation
pCFDPPDcfdpPduAggregationMaxSize OBJECT IDENTIFIER ::=
								{rtnCfdpPduBuffDelExtendedProcParam	3}

PCFDPPDcfdpPduAggregationMaxSizeType ::= INTEGER					

pCFDPPDcfdpPduAggregationTimeout OBJECT IDENTIFIER ::=
								{rtnCfdpPduBuffDelExtendedProcParam	4}

PCFDPPDcfdpPduAggregationTimeoutType ::= INTEGER

END
